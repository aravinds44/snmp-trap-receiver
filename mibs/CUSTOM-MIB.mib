-- Custom Enterprise MIB for demonstration
-- Replace 12345 with your actual enterprise number

CUSTOM-MIB DEFINITIONS ::= BEGIN

IMPORTS
    MODULE-IDENTITY, OBJECT-TYPE, NOTIFICATION-TYPE,
    Integer32, enterprises                    FROM SNMPv2-SMI
    TEXTUAL-CONVENTION, DisplayString         FROM SNMPv2-TC
    MODULE-COMPLIANCE, OBJECT-GROUP,
    NOTIFICATION-GROUP                        FROM SNMPv2-CONF;

customMIB MODULE-IDENTITY
    LAST-UPDATED  "202501010000Z"
    ORGANIZATION  "Example Organization"
    CONTACT-INFO
        "Example Admin
        Email: admin@example.com"
    DESCRIPTION
        "Custom MIB for demonstration purposes."
    REVISION      "202501010000Z"
    DESCRIPTION
        "Initial version."
    ::= { enterprises 12345 }

-- MIB Structure

customObjects     OBJECT IDENTIFIER ::= { customMIB 1 }
customTraps       OBJECT IDENTIFIER ::= { customMIB 2 }
customConformance OBJECT IDENTIFIER ::= { customMIB 3 }

-- Custom Objects

customAlerts      OBJECT IDENTIFIER ::= { customObjects 1 }
customStatus      OBJECT IDENTIFIER ::= { customObjects 2 }

-- Alert Message Object

customAlertMessage OBJECT-TYPE
    SYNTAX        DisplayString (SIZE (0..255))
    MAX-ACCESS    read-only
    STATUS        current
    DESCRIPTION
        "A custom alert message."
    ::= { customAlerts 1 }

-- Alert Severity Object

customAlertSeverity OBJECT-TYPE
    SYNTAX        Integer32 (1..100)
    MAX-ACCESS    read-only
    STATUS        current
    DESCRIPTION
        "Severity level of the custom alert (1-100)."
    ::= { customAlerts 2 }

-- System Status Object

customSystemStatus OBJECT-TYPE
    SYNTAX INTEGER {
        normal(1),
        warning(2),
        critical(3),
        unknown(4)
    }
    MAX-ACCESS    read-only
    STATUS        current
    DESCRIPTION
        "Overall system status."
    ::= { customStatus 1 }

-- Custom Trap Definitions

customAlertTrap NOTIFICATION-TYPE
    OBJECTS { customAlertMessage, customAlertSeverity }
    STATUS  current
    DESCRIPTION
        "A custom alert trap containing message and severity."
    ::= { customTraps 1 }

customStatusChangeTrap NOTIFICATION-TYPE
    OBJECTS { customSystemStatus }
    STATUS  current
    DESCRIPTION
        "A trap sent when system status changes."
    ::= { customTraps 2 }

END

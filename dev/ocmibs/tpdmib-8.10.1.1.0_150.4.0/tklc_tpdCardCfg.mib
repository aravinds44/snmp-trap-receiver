-- *****************************************************************************
-- Copyright (C) 2003, 2016, Oracle and/or its affiliates. All rights reserved.
-- *****************************************************************************
TPD-CARD-CFG-MIB DEFINITIONS ::= BEGIN

IMPORTS
    MODULE-IDENTITY,
    OBJECT-TYPE,
    IpAddress,
    Integer32,
    NOTIFICATION-TYPE         FROM SNMPv2-SMI
    TEXTUAL-CONVENTION,
    MacAddress, DisplayString FROM SNMPv2-TC
    tekelecTPD                FROM TEKELEC-TOPLEVEL-REG;

tpdCardCfg         MODULE-IDENTITY
    LAST-UPDATED "201412170000Z"
    ORGANIZATION "Tekelec, Inc."
    CONTACT-INFO "
         Postal: Tekelec, Inc.
                 5200 Paramount Parkway
                 Morrisville, NC 27560
                 USA

        Website: http://www.tekelec.com/support/

          Email: support@tekelec.com

            Tel:
    US & Canada: 888.367.8552
          India: +91.124.436.8552
          China: +65.6248.4510
    UK & Europe: +44.1784.467.804"

    DESCRIPTION
        "This MIB defines the data and notifications used by a System Manager
         in the process of discovering and configuring a device in an ATCA
         chassis running TPD.
         Copyright (C) Tekelec, Inc."

-- --------------------------------------------------------------------------
--                             REVISION HISTORY
--  
--  There should be one REVISION/DESCRIPTION pair for each revision of the
--  file.  Revisions should appear in reverse chronological order (the newest
--  revision at the top).
-- --------------------------------------------------------------------------
    REVISION "201412170000Z"
    DESCRIPTION
        "Updated Oracle copyright for 2015."

    REVISION "201405070000Z"
    DESCRIPTION
        "Update copyright information"

    REVISION "201303260000Z"
    DESCRIPTION
        "Removing IPMI FRU information for PR 225912"

    REVISION "201209190000Z"
    DESCRIPTION
        "PR 216289: MIB compilation fixes
         PR 127698: Resolve tklc_tpdCardCfg warnings"

    REVISION "201207110000Z"
    DESCRIPTION
        "Enhancing as per FE007019"

    REVISION "201012060000Z"
    DESCRIPTION
        "Marked obsolete MIB values as deprecated."

    REVISION "200912220000Z"
    DESCRIPTION
        "Changed syntax to allow compilation with mib compiler"

    REVISION "200708310000Z"
    DESCRIPTION
        "Added support for LED control on ATCA blades"

    REVISION "200705020000Z"
    DESCRIPTION
        "Added support for the short application name"

    REVISION "200607110000Z"
    DESCRIPTION
        "Added software and hardware inventory data."

    REVISION "200606090000Z"
    DESCRIPTION
        "Added upgrade configuration and status tracking."

    REVISION "200605080000Z"
    DESCRIPTION
        "Initial version"

    ::= { tekelecTPD 1 }

-- --------------------------------------------------------------------------
--                              TEXTUAL CONVENTIONS
-- --------------------------------------------------------------------------
IpmiFruInfoString ::=
    OCTET STRING (SIZE (0..255))
        -- The IPMI Platform Management FRU Information Storage
        -- Definition document typically defines that display strings can be
        -- variable length, up to 255 bytes.  

IpmiCardAddr ::=
    Integer32 ( '82'h | '84'h | '86'h | '88'h | '8A'h | '8C'h | '8E'h | '90'h |
              '92'h | '94'h | '96'h | '98'h | '9A'h | '9C'h | '9E'h | 'A0'h )
       -- IPMI address of a device.

DiskIndex ::= TEXTUAL-CONVENTION
    STATUS       current
    DESCRIPTION  "The number of possible disks on a device."
    SYNTAX       Integer32 (1..65536)

-- --------------------------------------------------------------------------
--                              CARD CONFIG DATA
-- --------------------------------------------------------------------------

tpdCardCfgData OBJECT IDENTIFIER ::= { tpdCardCfg 1 }

tpdCardCfgProductSerialNumber	OBJECT-TYPE
	SYNTAX		IpmiFruInfoString
	MAX-ACCESS	read-only
	STATUS		current
	DESCRIPTION
		"This object contains the Product Serial Number field (if any) from
         the device's Product Info Area.  If the field is not present on the
         device, this field shall contain a zero-length display string."
	::= { tpdCardCfgData 1 }

tpdCardCfgBoardSerialNumber	OBJECT-TYPE
	SYNTAX		IpmiFruInfoString
	MAX-ACCESS	read-only
	STATUS		current
	DESCRIPTION
		"This object contains the Board Serial Number field (if any) from
         the device's Board Info Area.  If the field is not present on the
         device, this field shall contain a zero-length display string."
	::= { tpdCardCfgData 5 }

tpdCardCfgBootIfname	OBJECT-TYPE
	SYNTAX		DisplayString
	MAX-ACCESS	read-only
	STATUS		current
	DESCRIPTION
        "The textual name of the interface that a device prefers to use for
         code-loading and boot purposes.  The value of this object should be
         the name of the interface as assigned by the local device and
         should be suitable for use in commands entered on the device,
         e.g. 'eth0'.  This MUST correspond to the interface indicated by
         'tpdCardCfgBootMacAddr'."
	::= { tpdCardCfgData 10 }

tpdCardCfgBootMacAddr	OBJECT-TYPE
	SYNTAX		MacAddress
	MAX-ACCESS	read-only
	STATUS		current
	DESCRIPTION
		"This object identifies the MAC address of the interface which a
         device prefers to use for code-loading and boot purposes.  This MUST 
         correspond to the interface indicated by 'tpdCardCfgBootIfname'."
	::= { tpdCardCfgData 11 }

tpdCardCfgState	OBJECT-TYPE
	SYNTAX		INTEGER { installed(1), up(2), down(3), installFailed(4),
                          beginRollback(5), endRollback(6) }
	MAX-ACCESS	read-only
	STATUS		current
	DESCRIPTION
		"This object identifies the current state of the TPD on the device.
         The value 'installed' indicates that TPD has been installed but is
         not currently running, and is generated at the end of the IPM
         process.  The value 'installFailed' indicates that an error was
		 detected by the IPM software, and IPM failed.  The values 'up' and
		 'down' are generated by the TPD itself as it initializes/shuts down.
         The values 'beginRollback' and 'endRollback' are used during 
         the processing of a software upgrade."
	::= { tpdCardCfgData 12 }

tpdCardCfgUserData	OBJECT-TYPE
	SYNTAX		OCTET STRING
	MAX-ACCESS	read-only
	STATUS		current
	DESCRIPTION
		"This object contains the value of the 'tklcuserdata' field passed 
         to the device on the KickStart command line.  If the field was not
         present on the command line, then this object contains a zero-length
         octet string.  The value of this object is not parsed by the TPD,
         and is only meaningful to the System Manager."
	::= { tpdCardCfgData 13 }

tpdCardCfgUpgradeServerAddr	OBJECT-TYPE
	SYNTAX		IpAddress
	MAX-ACCESS	read-write
	STATUS		deprecated
	DESCRIPTION
		"This object contains the IP address of the server that the device
         will attempt to use to upgrade its software on the next successful
         set of the variable 'tpdCardCfgStartUpgrade', below."
	::= { tpdCardCfgData 14 }

tpdCardCfgUpgradeImagePath	OBJECT-TYPE
	SYNTAX		OCTET STRING
	MAX-ACCESS	read-write
	STATUS		deprecated
	DESCRIPTION
		"This object contains a full path to an upgrade image that the 
         device will attempt to use to upgrade its software on the next
         successful set of the variable 'tpdCardCfgStartUpgrade', below.
         This path is assumed to be an NFS-mountable path on the server
         specified in 'tpdCardCfgUpgradeServerAddr'.  Furthermore, it
         is assumed to be a path to a loop-mounted upgrade image."
	::= { tpdCardCfgData 15 }

tpdCardCfgStartUpgrade	OBJECT-TYPE
	SYNTAX		Integer32
	MAX-ACCESS	read-write
	STATUS		deprecated
	DESCRIPTION
		"This object is used to initiate a software upgrade of the device.
         In order for a set to this variable to succeed, the variables
         'tpdCardCfgUpgradeServerAddr' and 'tpdCardCfgUpgradeImagePath'
         must be set in the same Set Request.  Upon a successful response
         to a set of this variable, 'tpdCardCfgUpgradeStatus' will have
         been initialized to report status of the requested upgrade.  If
         the set of this object fails for any reason, the object
         'tpdCardCfgStartUpgradeStatusText' will be updated to contain
         a more specific failure reason than that returnable in the SNMP
         Response PDU."
	::= { tpdCardCfgData 16 }

tpdCardCfgStartUpgradeStatusText	OBJECT-TYPE
	SYNTAX		OCTET STRING
	MAX-ACCESS	read-only
	STATUS		deprecated
	DESCRIPTION
		"This object contains a textual description of the results of
         the last attempt to set 'tpdCardCfgStartUpgrade'.  In the case
         that the set to 'tpdCardCfgStartUpgrade' failed, this object
         may be used to determine a more specific failure reason than
         that provided in the response to the set."
	::= { tpdCardCfgData 17 }

tpdCardCfgUpgradeStatus	OBJECT-TYPE
	SYNTAX		OCTET STRING
	MAX-ACCESS	read-only
	STATUS		deprecated
	DESCRIPTION
		"This object is used to report the status of an initiated upgrade.
         Upon a successful set of 'tpdCardCfgStartUpgrade', this object
         is initialized to a value reflecting the new upgrade.  If a 
         set of 'tpdCardCfgStartUpgrade' fails for any reason, the value
         of this object is not changed."
	::= { tpdCardCfgData 18 }

tpdCardCfgAppName	OBJECT-TYPE
	SYNTAX		OCTET STRING
	MAX-ACCESS	read-only
	STATUS		current
	DESCRIPTION
		"This object contains the high-level name of the application
         (e.g. TekCore)."
	::= { tpdCardCfgData 19 }

tpdCardCfgAppVersion	OBJECT-TYPE
	SYNTAX		OCTET STRING
	MAX-ACCESS	read-only
	STATUS		current
	DESCRIPTION
		"This object contains the version of the application."
	::= { tpdCardCfgData 20 }

tpdCardCfgDeviceFunction	OBJECT-TYPE
	SYNTAX		OCTET STRING
	MAX-ACCESS	read-only
	STATUS		current
	DESCRIPTION
		"This object contains a description of the high-level function
         of the device (MP server, DB server, etc.)."
	::= { tpdCardCfgData 21 }

tpdCardCfgDeviceDesignation	OBJECT-TYPE
	SYNTAX		OCTET STRING
	MAX-ACCESS	read-only
	STATUS		current
	DESCRIPTION
		"This object contains the designation of the device (application
         definition of physical location)."
	::= { tpdCardCfgData 22 }

tpdCardCfgPlatformSwName	OBJECT-TYPE
	SYNTAX		OCTET STRING
	MAX-ACCESS	read-only
	STATUS		current
	DESCRIPTION
		"This object contains the textual name of the Platform Software
         running on the device (e.g. TPD)."
	::= { tpdCardCfgData 23 }

tpdCardCfgPlatformSwVersion	OBJECT-TYPE
	SYNTAX		OCTET STRING
	MAX-ACCESS	read-only
	STATUS		current
	DESCRIPTION
		"This object contains the version of the Platform Software
         running on the device (e.g. 3.0.0-60.7.0)."
	::= { tpdCardCfgData 24 }

tpdCardCfgBiosMfg	OBJECT-TYPE
	SYNTAX		OCTET STRING
	MAX-ACCESS	read-only
	STATUS		deprecated
	DESCRIPTION
		"This object contains the name of the device's BIOS Manufacturer."
	::= { tpdCardCfgData 25 }

tpdCardCfgBiosVersion	OBJECT-TYPE
	SYNTAX		OCTET STRING
	MAX-ACCESS	read-only
	STATUS		deprecated
	DESCRIPTION
		"This object contains the version of the device's BIOS."
	::= { tpdCardCfgData 26 }

tpdCardCfgNumDisks OBJECT-TYPE
    SYNTAX      Integer32
    MAX-ACCESS  read-only
    STATUS      deprecated
    DESCRIPTION "An integer containing the number of disk entries in the
                 tpdCardCfgDiskTable."
    ::= { tpdCardCfgData 27 }

tpdCardCfgDiskTable OBJECT-TYPE
    SYNTAX      SEQUENCE OF TpdCardCfgDiskEntry
    MAX-ACCESS  not-accessible
    STATUS      deprecated
    DESCRIPTION "A list of disk entries.  The number of entries is given
                 by the value of tpdCardCfgNumDisks."
    ::= { tpdCardCfgData 28 }

tpdCardCfgDiskEntry OBJECT-TYPE
    SYNTAX      TpdCardCfgDiskEntry
    MAX-ACCESS  not-accessible
    STATUS      deprecated
    DESCRIPTION "An entry containing management information applicable to a
                 particular disk."
    INDEX       { tpdCardCfgDiskIndex }
    ::= { tpdCardCfgDiskTable 1 }

tpdCardCfgAppShortName	OBJECT-TYPE
	SYNTAX		OCTET STRING
	MAX-ACCESS	read-only
	STATUS		current
	DESCRIPTION
		"This object contains a shorter version of the high-level name of the application
         (e.g. TekCore)."
	::= { tpdCardCfgData 29 }

tpdCardCfgLedAColor	OBJECT-TYPE
	SYNTAX		OCTET STRING
	MAX-ACCESS	read-write
	STATUS		deprecated
	DESCRIPTION
		"This object contains the color of the User Definable A LED on
         an ATCA blade.  The options are red, green, amber and off.  In
         addition, the color can be preceded by blink which means the
         LED is blinking.  The exception to this is off which makes no
         sense."
	::= { tpdCardCfgData 30 }

tpdCardCfgLedBColor	OBJECT-TYPE
	SYNTAX		OCTET STRING
	MAX-ACCESS	read-write
	STATUS		deprecated
	DESCRIPTION
		"This object contains the color of the User Definable B LED on
         an ATCA blade.  The options are red, green, amber and off.  In
         addition, the color can be preceded by blink which means the
         LED is blinking.  The exception to this is off which makes no
         sense."
	::= { tpdCardCfgData 31 }


TpdCardCfgDiskEntry ::=
    SEQUENCE {
        tpdCardCfgDiskIndex         DiskIndex,
        tpdCardCfgDiskMfg           DisplayString,
        tpdCardCfgDiskSize          Integer32,
        tpdCardCfgDiskSerialNum     DisplayString,
        tpdCardCfgDiskModel         DisplayString,
        tpdCardCfgDiskFwVersion     DisplayString,
        tpdCardCfgDiskPoweredHours  Integer32,
        tpdCardCfgDiskName          DisplayString
    }

tpdCardCfgDiskIndex OBJECT-TYPE
    SYNTAX      DiskIndex
    MAX-ACCESS  read-only
    STATUS      deprecated
    DESCRIPTION "A unique value, greater than zero, for each disk.  It
                 is recommended that values are assigned contiguously
                 starting from 1.  The value for each disk must remain
                 constant at least from one re-initialization of the entity's
                 network management system to the next reinitialization."
    ::= { tpdCardCfgDiskEntry 1 }

tpdCardCfgDiskMfg OBJECT-TYPE
    SYNTAX      DisplayString
    MAX-ACCESS  read-only
    STATUS      deprecated
    DESCRIPTION "A textual string containing information about the disk's
                 manufacturer."
    ::= { tpdCardCfgDiskEntry 2 }

tpdCardCfgDiskSize OBJECT-TYPE
    SYNTAX      Integer32
    MAX-ACCESS  read-only
    STATUS      deprecated
    DESCRIPTION "An integer containing the size of the disk, in units
                 of 1K (1024) bytes."
    ::= { tpdCardCfgDiskEntry 3 }

tpdCardCfgDiskSerialNum OBJECT-TYPE
    SYNTAX      DisplayString
    MAX-ACCESS  read-only
    STATUS      deprecated
    DESCRIPTION "A textual string containing the disk's serial number."
    ::= { tpdCardCfgDiskEntry 4 }

tpdCardCfgDiskModel OBJECT-TYPE
    SYNTAX      DisplayString
    MAX-ACCESS  read-only
    STATUS      deprecated
    DESCRIPTION "A textual string containing the disk's model name."
    ::= { tpdCardCfgDiskEntry 5 }

tpdCardCfgDiskFwVersion OBJECT-TYPE
    SYNTAX      DisplayString
    MAX-ACCESS  read-only
    STATUS      deprecated
    DESCRIPTION "A textual string containing the disk's firmware version."
    ::= { tpdCardCfgDiskEntry 6 }

tpdCardCfgDiskPoweredHours OBJECT-TYPE
    SYNTAX      Integer32
    MAX-ACCESS  read-only
    STATUS      deprecated
    DESCRIPTION "An integer containing the cumulative number of hours the disk
                 has been powered-on through it's lifetime."
    ::= { tpdCardCfgDiskEntry 7 }

tpdCardCfgDiskName OBJECT-TYPE
    SYNTAX      DisplayString
    MAX-ACCESS  read-only
    STATUS      deprecated
    DESCRIPTION "A textual string containing the disk's name (e.g. sda1)."
    ::= { tpdCardCfgDiskEntry 8 }

-- Details on VLAN stuff, port bonding stuff will go here.

-- --------------------------------------------------------------------------
--                             TRAPS/NOTIFICATIONS
-- --------------------------------------------------------------------------

tpdCardCfgNotifications OBJECT IDENTIFIER ::= { tpdCardCfg 2 }

tpdNotifyMblCardPresent		NOTIFICATION-TYPE
    OBJECTS { tpdCardCfgProductSerialNumber,
              tpdCardCfgBoardSerialNumber,
              tpdCardCfgBootIfname,
              tpdCardCfgBootMacAddr }
    STATUS  current
    DESCRIPTION
        "This notification is sent by MBL to the System Manager
         whenever a new card comes on-line."
	::= { tpdCardCfgNotifications 1 }

tpdNotifyIpmPostinstall        NOTIFICATION-TYPE
    OBJECTS { tpdCardCfgUserData,
              tpdCardCfgState }
    STATUS  current
    DESCRIPTION
        "This notification is sent by IPM on a device to the System
         Manager whenever the device has been loaded with TPD,
         but before TPD runs.  The value of tpdCardState will be either
		 'installed' or 'installFailed'."
    ::= { tpdCardCfgNotifications 2 }

tpdNotifyTpdStateChange		NOTIFICATION-TYPE
    OBJECTS { tpdCardCfgProductSerialNumber,
              tpdCardCfgBoardSerialNumber,
              tpdCardCfgState }
    STATUS  current
    DESCRIPTION
        "This notification is sent by the TPD on a device to notify the 
         System Manager of a change in state."

	::= { tpdCardCfgNotifications 3 }

END
-- vi:ts=4 sw=4:nohls:et:

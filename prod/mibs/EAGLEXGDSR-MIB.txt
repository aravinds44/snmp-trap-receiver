--
-- Copyright (C) 2012, 2014, Oracle and/or its affiliates. All rights reserved.
-- $Id$
--
EAGLEXGDSR-MIB DEFINITIONS ::= BEGIN

IMPORTS
    MODULE-IDENTITY, OBJECT-TYPE, NOTIFICATION-TYPE, Counter32, TimeTicks,
    Integer32, Unsigned32
                                                FROM SNMPv2-SMI
    TEXTUAL-CONVENTION, DisplayString, PhysAddress, TruthValue
                                                FROM SNMPv2-TC
    TimeFilter                                  FROM RMON2-MIB
    tekelecEAGLEXGDSR                              FROM TEKELEC-TOPLEVEL-REG
    EagleXgDsrNodeId,  EagleXgDsrAlarmSeverity, EagleXgDsrAlarmNumber, EagleXgDsrDateAndTime,
    EagleXgDsrTaskName, EagleXgDsrMergePartNum, EagleXgDsrNodeCap, EagleXgDsrNodeCapability, 
    EagleXgDsrAlarmGroup, EagleXgDsrTelemetryName, EagleXgDsrTelemetryType, EagleXgDsrEventType,
    EagleXgDsrTelemetrySource, EagleXgDsrTelemetryBasis, EagleXgDsrTelemetryId
                                                FROM EAGLEXGDSR-TC;

eagleXgDsrMIB MODULE-IDENTITY
    LAST-UPDATED "201210011308Z"
    ORGANIZATION "Tekelec, Inc."
    CONTACT-INFO
            "   Tekelec, Inc.
                5200 Paramount Parkway
                Morrisville, NC 27560
                USA

                http://www.tekelec.com/support/
                US & Canada: 888.367.8552
                India: +91.124.436.8552
                China: +65.6248.4510
                UK & Europe: +44.1784.467.804"
    DESCRIPTION
            "Updated contact information, added descriptions for all of the MIB
            variables that were missing descriptions and removed the IMPLIED
            keyword from the index to eagleXgDsrSiteInfoEntry."
    REVISION    "201210011308Z"
    DESCRIPTION
            "Added new varbind - eagleXgDsrAlarmSrcName to EagleXgDsrAlarmEntry
            to satisfy requirement# 1313 of PR 209807"
    REVISION    "201207311924Z"
    DESCRIPTION
            "Updated contact information."
    REVISION    "201207161413Z"
    DESCRIPTION
            "Added new table EagleXgDsrSiteInfoTable to eagleXgDsrSystem. 
            Added eagleXgDsrServerNodeCapability, eagleXgDsrServerInhibitRepPlans,
            and eagleXgDsrServerSiteId to eagleXgDsrNodeInfoEntry, and deprecated
            eagleXgDsrServerInhibitFlag and eagleXgDsrServerNodeCap."
    REVISION    "201205181730Z"
    DESCRIPTION
            "Added eagleXgDsrAlarmSequence varbind and added
            eagleXgDsrServerHostname, eagleXgDsrAlarmSequence and
            eagleXgDsrAlarmTimestamp to alarm traps.
            Updated contact information."
    REVISION    "201203301715Z"
    DESCRIPTION
            "Removed IMPLIED keyword on the alarm and telemetry tables."
    REVISION    "201111041226Z"
    DESCRIPTION
            "Updates to telemetry tables."
    REVISION    "200906291536Z"
    DESCRIPTION
            "Updates for MIB formatting compliance."
    REVISION    "200905201536Z"
    DESCRIPTION
            "The MIB module for managing EAGLEXGDSR implementations.
             Copyright (C) Tekelec, Inc."
    ::= { tekelecEAGLEXGDSR 1 }

--
-- MIB tables and variables definition
--
eagleXgDsrMIBObjects   OBJECT IDENTIFIER ::= { eagleXgDsrMIB 1 }

eagleXgDsrSystem       OBJECT IDENTIFIER ::= { eagleXgDsrMIBObjects 1 }

eagleXgDsrServerLocalName OBJECT-TYPE
    SYNTAX      DisplayString (SIZE (0..255))
    MAX-ACCESS  read-only
    STATUS      current
    DESCRIPTION
            "The hostname of the server."
    ::= { eagleXgDsrSystem 1 }

eagleXgDsrServerLocalNodeId OBJECT-TYPE
    SYNTAX      EagleXgDsrNodeId
    MAX-ACCESS  read-only
    STATUS      current
    DESCRIPTION
            "The node ID of the server. Each server in the topology is assigned
            a unique node ID that identifies its level, cluster number and
            member number."
    ::= { eagleXgDsrSystem 2 }

eagleXgDsrNodeInfoLastChangeTime OBJECT-TYPE
    SYNTAX      TimeTicks
    MAX-ACCESS  read-only
    STATUS      current
    DESCRIPTION
            "The time when the NodeInfo table last changed."
    ::= { eagleXgDsrSystem 3 }

eagleXgDsrNodeInfoTable OBJECT-TYPE
    SYNTAX      SEQUENCE OF EagleXgDsrNodeInfoEntry
    MAX-ACCESS  not-accessible
    STATUS      current
    DESCRIPTION
            "The contents of the NodeInfo topology table containing identifying
            information about each server provisioning in the network topology."
    ::= { eagleXgDsrSystem 4 }

eagleXgDsrNodeInfoEntry OBJECT-TYPE
    SYNTAX      EagleXgDsrNodeInfoEntry
    MAX-ACCESS  not-accessible
    STATUS      current
    DESCRIPTION
            "An entry in the NodeInfo topology table. This table is indexed by
            a node ID that is required to be unique for each server in the
            network topology."
    INDEX { IMPLIED eagleXgDsrServerNodeId }
    ::= { eagleXgDsrNodeInfoTable 1 }

EagleXgDsrNodeInfoEntry ::=
    SEQUENCE {
        eagleXgDsrServerNodeId          EagleXgDsrNodeId,
        eagleXgDsrServerNodeName        DisplayString,
        eagleXgDsrServerHostname        DisplayString,
        eagleXgDsrServerInhibitFlag     BITS,
        eagleXgDsrServerNodeCap         EagleXgDsrNodeCap,
        eagleXgDsrServerExcludedTables  DisplayString,
        eagleXgDsrServerNodeCapability  EagleXgDsrNodeCapability,
        eagleXgDsrServerInhibitRepPlans DisplayString,
        eagleXgDsrServerSiteId          INTEGER
    }

eagleXgDsrServerNodeId OBJECT-TYPE
    SYNTAX      EagleXgDsrNodeId
    MAX-ACCESS  not-accessible
    STATUS      current
    DESCRIPTION
            "Unique node ID identifying the server. The node ID identifies the
            level (A, B or C), cluster ID number and member server number."
    ::= { eagleXgDsrNodeInfoEntry 1 }

eagleXgDsrServerNodeName OBJECT-TYPE
    SYNTAX      DisplayString
    MAX-ACCESS  read-only
    STATUS      current
    DESCRIPTION
            "Text name for a server in the network topology. This name may or
            may not match the hostname, but usually is the same as the
            hostname."
    ::= { eagleXgDsrNodeInfoEntry 2 }

eagleXgDsrServerHostname OBJECT-TYPE
    SYNTAX      DisplayString
    MAX-ACCESS  read-only
    STATUS      current
    DESCRIPTION
            "Hostname for a server in the network topology. This hostname
            matches the hostname of the server as configured in the operating
            system."
    ::= { eagleXgDsrNodeInfoEntry 3 }

eagleXgDsrServerInhibitFlag OBJECT-TYPE
    SYNTAX      BITS {
                    outOfService(0),
                    inetSync(1),
                    inetBroad(2),
                    inetMerge(3),
                    testApp(4),
                    haApp(5)
                }
    MAX-ACCESS  read-only
    STATUS      deprecated
    DESCRIPTION
            "Flag to control the level of service being provided by a server.
            No bits set means that the server is enabled for replication,
            merging/collection and high availability.

            Setting the outOfService(0) bit disables replication to this
            server, disables merging/collection from this server and sets the
            server to a forced standby high availability state. In addition,
            any alarms that may be present related to these services on this
            server are disabled.

            Setting the inetSync(1) bit disables replication to this server.

            The inetBroad(2) bit is obsolete and unused.

            The inetMerge(3) bit disables merging / collection from this
            server.

            The testApp(4) bit is used for testing purposes only and is not
            intended for end users.

            The haApp(5) bit disables high availability and causes the server
            to be placed in a forced standby state."
    ::= { eagleXgDsrNodeInfoEntry 4 }

eagleXgDsrServerNodeCap OBJECT-TYPE
    SYNTAX      EagleXgDsrNodeCap
    MAX-ACCESS  read-only
    STATUS      deprecated
    DESCRIPTION
            "This flag controls whether the server actively participates in
            high availability or not. Normally this value should be set to
            masterCapable(0) for servers actively providing service. The
            exception is query servers where this value should be none(1)."
    ::= { eagleXgDsrNodeInfoEntry 5 }

eagleXgDsrServerExcludedTables OBJECT-TYPE
    SYNTAX      DisplayString
    MAX-ACCESS  read-only
    STATUS      deprecated
    DESCRIPTION
            "Space-separated list of table names excluded from database
            replication."
    ::= { eagleXgDsrNodeInfoEntry 6 }

eagleXgDsrServerNodeCapability OBJECT-TYPE
    SYNTAX      EagleXgDsrNodeCapability
    MAX-ACCESS  read-only
    STATUS      current
    DESCRIPTION
            "Highest high availability role the server is capable of being
            assigned. Servers fully in service have this value set to active(4)
            while servers in maintenance states will have lower values set to
            limit the role the server is assigned. For example, servers in
            forced standby will have this value set to standby(3) and server in
            an out-of-service maintenance state will have this value set to
            oos(0)."
    ::= { eagleXgDsrNodeInfoEntry 7 }

eagleXgDsrServerInhibitRepPlans OBJECT-TYPE
    SYNTAX      DisplayString
    MAX-ACCESS  read-only
    STATUS      current
    DESCRIPTION
            "Space-separated list of database replication plans that are
            inhibited from replication to the server. Replication plans are a
            grouping of related database tables for the purpose of managing
            their replication across servers."
    ::= { eagleXgDsrNodeInfoEntry 8 }

eagleXgDsrServerSiteId OBJECT-TYPE
    SYNTAX      INTEGER
    MAX-ACCESS  read-only
    STATUS      current
    DESCRIPTION
            "Identification number corresponding to the site ID of the site in
            which the server is located. A site ID of 0 corresponds to
            Unspecified and indicates that no server site ID has been
            provisioned."
    ::= { eagleXgDsrNodeInfoEntry 9 }

eagleXgDsrSiteInfoTable OBJECT-TYPE
    SYNTAX      SEQUENCE OF EagleXgDsrSiteInfoEntry
    MAX-ACCESS  not-accessible
    STATUS      current
    DESCRIPTION
            "Table containing the name and ID number of all of the sites in the
            network topology."
    ::= { eagleXgDsrSystem 5 }

eagleXgDsrSiteInfoEntry OBJECT-TYPE
    SYNTAX      EagleXgDsrSiteInfoEntry
    MAX-ACCESS  not-accessible
    STATUS      current
    DESCRIPTION
            "An entry in the SiteInfo table. This table is indexed by a numeric
            site ID number."
    INDEX { eagleXgDsrSiteId }
    ::= { eagleXgDsrSiteInfoTable 1 }

EagleXgDsrSiteInfoEntry ::=
    SEQUENCE {
        eagleXgDsrSiteId          INTEGER,
        eagleXgDsrSiteName        DisplayString
    }

eagleXgDsrSiteId    OBJECT-TYPE
    SYNTAX      INTEGER (0..65535)
    MAX-ACCESS  not-accessible
    STATUS      current
    DESCRIPTION
            "Unique identification number for the site."
    ::= { eagleXgDsrSiteInfoEntry 1 }

eagleXgDsrSiteName  OBJECT-TYPE
    SYNTAX      DisplayString
    MAX-ACCESS  read-only
    STATUS      current
    DESCRIPTION
            "Name of the site."
    ::= { eagleXgDsrSiteInfoEntry 2 }

eagleXgDsrIdb          OBJECT IDENTIFIER ::= { eagleXgDsrMIBObjects 2 }

eagleXgDsrIdbTable OBJECT-TYPE
    SYNTAX      SEQUENCE OF EagleXgDsrIdbEntry
    MAX-ACCESS  not-accessible
    STATUS      current
    DESCRIPTION
            "Table providing generic access to database table contents. Access
            is provided in such a way that database table contents are
            available as raw octets without a specific MIB needed."
    ::= { eagleXgDsrIdb 1 }

eagleXgDsrIdbEntry OBJECT-TYPE
    SYNTAX      EagleXgDsrIdbEntry
    MAX-ACCESS  not-accessible
    STATUS      current
    DESCRIPTION
            "Entry for generic access to a database table record."
    INDEX   { eagleXgDsrIdbTableId, eagleXgDsrIdbSubpart, eagleXgDsrIdbFragment,
              eagleXgDsrIdbRecordId, eagleXgDsrIdbFieldId }
    ::= { eagleXgDsrIdbTable 1 }

EagleXgDsrIdbEntry ::=
    SEQUENCE {
        eagleXgDsrIdbTableId        Integer32,
        eagleXgDsrIdbSubpart        Integer32,
        eagleXgDsrIdbFragment       Integer32,
        eagleXgDsrIdbRecordId       Integer32,
        eagleXgDsrIdbFieldId        Integer32,
        eagleXgDsrIdbData           OCTET STRING
    }

eagleXgDsrIdbTableId OBJECT-TYPE
    SYNTAX      Integer32 (0..2147483647)
    MAX-ACCESS  not-accessible
    STATUS      current
    DESCRIPTION
            "Unique table identification number in the database data
            dictionary."
    ::= { eagleXgDsrIdbEntry 1 }

eagleXgDsrIdbSubpart OBJECT-TYPE
    SYNTAX      Integer32 (0..2147483647)
    MAX-ACCESS  not-accessible
    STATUS      current
    DESCRIPTION
            "Subpart number of the table. For tables with no subparts, this
            value will always be zero."
    ::= { eagleXgDsrIdbEntry 2 }

eagleXgDsrIdbFragment OBJECT-TYPE
    SYNTAX      Integer32 (0..2147483647)
    MAX-ACCESS  not-accessible
    STATUS      current
    DESCRIPTION
            "Unique database fragment identifier for the given table ID and
            subpart."
    ::= { eagleXgDsrIdbEntry 3 }

eagleXgDsrIdbRecordId OBJECT-TYPE
    SYNTAX      Integer32 (0..2147483647)
    MAX-ACCESS  not-accessible
    STATUS      current
    DESCRIPTION
            "Physical record ID number of a record."
    ::= { eagleXgDsrIdbEntry 4 }

eagleXgDsrIdbFieldId OBJECT-TYPE
    SYNTAX      Integer32 (0..2147483647)
    MAX-ACCESS  not-accessible
    STATUS      current
    DESCRIPTION
            "Field ID number of a field in a record in the table."
    ::= { eagleXgDsrIdbEntry 5 }

eagleXgDsrIdbData OBJECT-TYPE
    SYNTAX      OCTET STRING
    MAX-ACCESS  read-only
    STATUS      current
    DESCRIPTION
            "Raw contents of a field in a database table."
    ::= { eagleXgDsrIdbEntry 6 }

eagleXgDsrAlarms  OBJECT IDENTIFIER ::= { eagleXgDsrMIBObjects 3 }

eagleXgDsrAlarmLocalCount OBJECT-TYPE
    SYNTAX      Integer32
    MAX-ACCESS  read-only
    STATUS      current
    DESCRIPTION
            "A count of the number of alarms currently asserted on the local
            server."
    ::= { eagleXgDsrAlarms 1 }

eagleXgDsrAlarmMergeCount OBJECT-TYPE
    SYNTAX      Integer32
    MAX-ACCESS  read-only
    STATUS      current
    DESCRIPTION
            "A count of the number of alarms currently stored in the merged
            alarm table."
    ::= { eagleXgDsrAlarms 2 }

eagleXgDsrAlarmLocalLastChangeTime OBJECT-TYPE
    SYNTAX      TimeTicks
    MAX-ACCESS  read-only
    STATUS      current
    DESCRIPTION
            "A timestamp containing the last time that the local alarm table
            changed."
    ::= { eagleXgDsrAlarms 3 }

eagleXgDsrAlarmMergeLastChangeTime OBJECT-TYPE
    SYNTAX      TimeTicks
    MAX-ACCESS  read-only
    STATUS      current
    DESCRIPTION
            "A timestamp containing the last time that the merged alarm table
            changed."
    ::= { eagleXgDsrAlarms 4 }

eagleXgDsrAlarmTable OBJECT-TYPE
    SYNTAX      SEQUENCE OF EagleXgDsrAlarmEntry
    MAX-ACCESS  not-accessible
    STATUS      current
    DESCRIPTION
            "A table containing details of the currently raised alarms, both
            local to the server and merged from other servers in the network
            topology."
    ::= { eagleXgDsrAlarms 5 }

eagleXgDsrAlarmEntry OBJECT-TYPE
    SYNTAX      EagleXgDsrAlarmEntry
    MAX-ACCESS  not-accessible
    STATUS      current
    DESCRIPTION
            "A single entry in the alarm table indexed by part (local or
            merged), source node ID, alarm ID number and alarm instance
            string."
    INDEX   { eagleXgDsrAlarmPart, eagleXgDsrAlarmSrcNode, eagleXgDsrAlarmNumber,
              eagleXgDsrAlarmInstance }
    ::= { eagleXgDsrAlarmTable 1 }


EagleXgDsrAlarmEntry ::=
    SEQUENCE {
        eagleXgDsrAlarmPart             EagleXgDsrMergePartNum,
        eagleXgDsrAlarmSrcNode          EagleXgDsrNodeId,
        eagleXgDsrAlarmNumber           EagleXgDsrAlarmNumber,
        eagleXgDsrAlarmInstance         DisplayString,
        eagleXgDsrAlarmTimestamp        EagleXgDsrDateAndTime,
        eagleXgDsrAlarmGroup            EagleXgDsrAlarmGroup,
        eagleXgDsrAlarmSeverity         EagleXgDsrAlarmSeverity,
        eagleXgDsrAlarmText             DisplayString,
        eagleXgDsrAlarmInfo             DisplayString,
        eagleXgDsrAlarmSrcName          DisplayString,
        eagleXgDsrAlarmEventType        EagleXgDsrEventType,
        eagleXgDsrAlarmProbableCause    DisplayString,
        eagleXgDsrAlarmAdditionalInfo   DisplayString,
        eagleXgDsrAlarmTrapName         DisplayString
    }

eagleXgDsrAlarmPart OBJECT-TYPE
    SYNTAX      EagleXgDsrMergePartNum
    MAX-ACCESS  read-only
    STATUS      current
    DESCRIPTION
            "Part number that identifies whether the alarm is a local alarm
            entry or a merged alarm entry."
    ::= { eagleXgDsrAlarmEntry 1 }

eagleXgDsrAlarmSrcNode OBJECT-TYPE
    SYNTAX      EagleXgDsrNodeId
    MAX-ACCESS  read-only
    STATUS      current
    DESCRIPTION
            "Source node ID number of the server originating the alarm. See the
            eagleXgDsrNodeInfo table for details. The source node is always all
            zeros for a local alarm and set to a valid node ID from the
            eagleXgDsrNodeInfo table for merged alarms."
    ::= { eagleXgDsrAlarmEntry 2 }

eagleXgDsrAlarmNumber OBJECT-TYPE
    SYNTAX      EagleXgDsrAlarmNumber
    MAX-ACCESS  read-only
    STATUS      current
    DESCRIPTION
            "Number identifying the specific alarm that is asserted."
    ::= { eagleXgDsrAlarmEntry 3 }

eagleXgDsrAlarmInstance OBJECT-TYPE
    SYNTAX      DisplayString
    MAX-ACCESS  read-only
    STATUS      current
    DESCRIPTION
            "String that supplies additional identifying information for the
            alarm. A combination of the alarm number and instance is what makes
            an alarm unique."
    ::= { eagleXgDsrAlarmEntry 4 }

eagleXgDsrAlarmTimestamp OBJECT-TYPE
    SYNTAX      EagleXgDsrDateAndTime
    MAX-ACCESS  read-only
    STATUS      current
    DESCRIPTION
            "Timestamp when the alarm was last raised."
    ::= { eagleXgDsrAlarmEntry 5 }

eagleXgDsrAlarmGroup OBJECT-TYPE
    SYNTAX      EagleXgDsrAlarmGroup
    MAX-ACCESS  read-only
    STATUS      current
    DESCRIPTION
            "Abbreviation indicating the category or group to which the alarm
            belongs."
    ::= { eagleXgDsrAlarmEntry 6 }

eagleXgDsrAlarmSeverity OBJECT-TYPE
    SYNTAX      EagleXgDsrAlarmSeverity
    MAX-ACCESS  read-only
    STATUS      current
    DESCRIPTION
            "Severity of the alarm."
    ::= { eagleXgDsrAlarmEntry 7 }

eagleXgDsrAlarmText OBJECT-TYPE
    SYNTAX      DisplayString
    MAX-ACCESS  read-only
    STATUS      current
    DESCRIPTION
            "Text name of the alarm."
    ::= { eagleXgDsrAlarmEntry 8 }

eagleXgDsrAlarmInfo OBJECT-TYPE
    SYNTAX      DisplayString
    MAX-ACCESS  read-only
    STATUS      current
    DESCRIPTION
            "Additional textual alarm information to assist in
            troubleshooting."
    ::= { eagleXgDsrAlarmEntry 9 }

eagleXgDsrAlarmSrcName OBJECT-TYPE
    SYNTAX      DisplayString
    MAX-ACCESS  read-only
    STATUS      current
    DESCRIPTION
            "Node name of the server that originated the alarm. Refer to the
            eagleXgDsrServerNodeName variable for more information."
    ::= { eagleXgDsrAlarmEntry 10 }


eagleXgDsrAlarmSequence OBJECT-TYPE
    SYNTAX      Unsigned32
    MAX-ACCESS  read-only
    STATUS      current
    DESCRIPTION
            "The current alarm sequence number."
    ::= { eagleXgDsrAlarms 6 }

eagleXgDsrAlarmEventType        OBJECT-TYPE
    SYNTAX      EagleXgDsrEventType
    MAX-ACCESS  read-only
    STATUS      current
    DESCRIPTION
            "The event type of current alarm."
    ::= { eagleXgDsrAlarmEntry 11 }

eagleXgDsrAlarmProbableCause    OBJECT-TYPE
    SYNTAX      DisplayString
    MAX-ACCESS  read-only
    STATUS      current
    DESCRIPTION
            "The probable cause of current alarm."
    ::= { eagleXgDsrAlarmEntry 12 }

eagleXgDsrAlarmAdditionalInfo   OBJECT-TYPE
    SYNTAX      DisplayString
    MAX-ACCESS  read-only
    STATUS      current
    DESCRIPTION
            "Comma-separated triplets of key flag, name and value."
    ::= { eagleXgDsrAlarmEntry 13 }

eagleXgDsrAlarmTrapName OBJECT-TYPE
    SYNTAX      DisplayString
    MAX-ACCESS  read-only
    STATUS      current
    DESCRIPTION
            "The SNMP Trap name of current alarm."
    ::= { eagleXgDsrAlarmEntry 14 }

eagleXgDsrTelemetry  OBJECT IDENTIFIER ::= { eagleXgDsrMIBObjects 4 }

eagleXgDsrTelemetryTableLastChangeTime  OBJECT-TYPE
    SYNTAX      TimeTicks
    MAX-ACCESS  read-only
    STATUS      current
    DESCRIPTION
            "The last time any telemetry information was updated."
    ::= { eagleXgDsrTelemetry 1 }

eagleXgDsrTelemetryDefTable OBJECT-TYPE
    SYNTAX      SEQUENCE OF EagleXgDsrTelemetryDefEntry
    MAX-ACCESS  not-accessible
    STATUS      current
    DESCRIPTION
            "Table containing the definitions of all of the telemetry data
            being collected."
    ::= { eagleXgDsrTelemetry 2 }

eagleXgDsrTelemetryDefEntry OBJECT-TYPE
    SYNTAX      EagleXgDsrTelemetryDefEntry
    MAX-ACCESS  not-accessible
    STATUS      current
    DESCRIPTION
            "Entry for the definition of a single piece of telemetry data,
            indexed by a unique identification number."
    INDEX { eagleXgDsrTelemetryDefId }
    ::= { eagleXgDsrTelemetryDefTable 1 }

EagleXgDsrTelemetryDefEntry ::=
    SEQUENCE {
        eagleXgDsrTelemetryDefId            EagleXgDsrTelemetryId,
        eagleXgDsrTelemetryDefName          EagleXgDsrTelemetryName,
        eagleXgDsrTelemetryDefType          EagleXgDsrTelemetryType,
        eagleXgDsrTelemetryDefSource        EagleXgDsrTelemetrySource,
        eagleXgDsrTelemetryDefGroup         EagleXgDsrTelemetryName,
        eagleXgDsrTelemetryDefGroupWeight   Integer32,
        eagleXgDsrTelemetryDefDeriveGroup   EagleXgDsrTelemetryName,
        eagleXgDsrTelemetryDefTotal         Unsigned32,
        eagleXgDsrTelemetryDefMerged        TruthValue,
        eagleXgDsrTelemetryDefSourceMeasId  INTEGER,
        eagleXgDsrTelemetryDefAvgInterval   Integer32,
        eagleXgDsrTelemetryDefDestMeasId1   INTEGER,
        eagleXgDsrTelemetryDefDestMeasId2   INTEGER,
        eagleXgDsrTelemetryDefSubNameTab    EagleXgDsrTelemetryName
    }

eagleXgDsrTelemetryDefId  OBJECT-TYPE
    SYNTAX      EagleXgDsrTelemetryId
    MAX-ACCESS  not-accessible
    STATUS      current
    DESCRIPTION
            "Unique ID number identifying the telemetry value."
    ::= { eagleXgDsrTelemetryDefEntry 1 }

eagleXgDsrTelemetryDefName  OBJECT-TYPE
    SYNTAX      EagleXgDsrTelemetryName
    MAX-ACCESS  read-only
    STATUS      current
    DESCRIPTION
            "Text name describing the telemetry value."
    ::= { eagleXgDsrTelemetryDefEntry 2 }

eagleXgDsrTelemetryDefType  OBJECT-TYPE
    SYNTAX      EagleXgDsrTelemetryType
    MAX-ACCESS  read-only
    STATUS      current
    DESCRIPTION
            "Enumerated value describing the type of the telemetry value."
    ::= { eagleXgDsrTelemetryDefEntry 3 }

eagleXgDsrTelemetryDefSource  OBJECT-TYPE
    SYNTAX      EagleXgDsrTelemetrySource
    MAX-ACCESS  read-only
    STATUS      current
    DESCRIPTION
            "Enumerated value describing the data source of the telemetry
            value."
    ::= { eagleXgDsrTelemetryDefEntry 4 }

eagleXgDsrTelemetryDefGroup  OBJECT-TYPE
    SYNTAX      EagleXgDsrTelemetryName
    MAX-ACCESS  read-only
    STATUS      current
    DESCRIPTION
            "Text name used to group related telemetry values."
    ::= { eagleXgDsrTelemetryDefEntry 5 }

eagleXgDsrTelemetryDefGroupWeight  OBJECT-TYPE
    SYNTAX      Integer32
    MAX-ACCESS  read-only
    STATUS      current
    DESCRIPTION
            "Relative weight of this telemetry value within its group."
    ::= { eagleXgDsrTelemetryDefEntry 6 }

eagleXgDsrTelemetryDefDeriveGroup  OBJECT-TYPE
    SYNTAX      EagleXgDsrTelemetryName
    MAX-ACCESS  read-only
    STATUS      current
    DESCRIPTION
            "For telemetry values calculated on a group of telemetry values,
            this value specifies the name of the group from which the telemetry
            values are derived."
    ::= { eagleXgDsrTelemetryDefEntry 7 }

eagleXgDsrTelemetryDefTotal  OBJECT-TYPE
    SYNTAX      Unsigned32
    MAX-ACCESS  read-only
    STATUS      current
    DESCRIPTION
            "Numeric total value for calculating percentages for percentage
            telemetry values."
    ::= { eagleXgDsrTelemetryDefEntry 8 }

eagleXgDsrTelemetryDefMerged  OBJECT-TYPE
    SYNTAX      TruthValue
    MAX-ACCESS  read-only
    STATUS      current
    DESCRIPTION
            "Boolean controlling whether the telemetry value is merged or not."
    ::= { eagleXgDsrTelemetryDefEntry 9 }

eagleXgDsrTelemetryDefSourceMeasId  OBJECT-TYPE
    SYNTAX      INTEGER
    MAX-ACCESS  read-only
    STATUS      current
    DESCRIPTION
            "Contains the measurement ID of the source measurement data for
            this telemetry value if the telemetry value is based on a
            measurement. If this telemetry value is not based on a measurement,
            it contains -1."
    ::= { eagleXgDsrTelemetryDefEntry 10 }

eagleXgDsrTelemetryDefAvgInterval  OBJECT-TYPE
    SYNTAX      Integer32
    MAX-ACCESS  read-only
    STATUS      current
    DESCRIPTION
            "Duration in seconds over which running average telemetry values
            are normalized."
    ::= { eagleXgDsrTelemetryDefEntry 11 }

eagleXgDsrTelemetryDefDestMeasId1  OBJECT-TYPE
    SYNTAX      INTEGER
    MAX-ACCESS  read-only
    STATUS      current
    DESCRIPTION
            "Contains a measurement ID of a destination measurement if the
            telemetry value is published into the measurements framework for
            inclusion in measurement reports. If not used, it contains -1."
    ::= { eagleXgDsrTelemetryDefEntry 12 }

eagleXgDsrTelemetryDefDestMeasId2  OBJECT-TYPE
    SYNTAX      INTEGER
    MAX-ACCESS  read-only
    STATUS      current
    DESCRIPTION
            "Contains a second measurement ID of a destination measurement if
            the telemetry value is published into the measurements framework
            for inclusion in measurement reports. If not used, it contains -1."
    ::= { eagleXgDsrTelemetryDefEntry 13 }

eagleXgDsrTelemetryDefSubNameTab  OBJECT-TYPE
    SYNTAX      EagleXgDsrTelemetryName
    MAX-ACCESS  read-only
    STATUS      current
    DESCRIPTION
            "Contains the name of a database table used for mapping arrayed
            telemetry values into a corresponding name. For non-arrayed
            telemetry values or telemetry values that do no map arrayed values
            into names, this will be empty."
    ::= { eagleXgDsrTelemetryDefEntry 14 }

eagleXgDsrTelemetryThreshTable OBJECT-TYPE
    SYNTAX      SEQUENCE OF EagleXgDsrTelemetryThreshEntry
    MAX-ACCESS  not-accessible
    STATUS      current
    DESCRIPTION
            "Table defining thresholds for telemetry values that, when
            exceeded, raise alarms."
    ::= { eagleXgDsrTelemetry 3 }

eagleXgDsrTelemetryThreshEntry OBJECT-TYPE
    SYNTAX      EagleXgDsrTelemetryThreshEntry
    MAX-ACCESS  not-accessible
    STATUS      current
    DESCRIPTION
            "A single telemetry threshold entry, indexed by threshold ID,
            function and severity."
    INDEX { eagleXgDsrTelemetryThreshId, eagleXgDsrTelemetryThreshFunction,
            eagleXgDsrTelemetryThreshSeverity }
    ::= { eagleXgDsrTelemetryThreshTable 1 }

EagleXgDsrTelemetryThreshEntry ::=
    SEQUENCE {
        eagleXgDsrTelemetryThreshId         EagleXgDsrTelemetryId,
        eagleXgDsrTelemetryThreshFunction   EagleXgDsrTelemetryName,
        eagleXgDsrTelemetryThreshBasis      EagleXgDsrTelemetryBasis,
        eagleXgDsrTelemetryThreshAlarm      EagleXgDsrAlarmNumber,
        eagleXgDsrTelemetryThreshSeverity   EagleXgDsrAlarmSeverity,
        eagleXgDsrTelemetryThreshSetThreshold   Unsigned32,
        eagleXgDsrTelemetryThreshClearThreshold Unsigned32,
        eagleXgDsrTelemetryThreshAbateTimeMs    Unsigned32
    }

eagleXgDsrTelemetryThreshId  OBJECT-TYPE
    SYNTAX      EagleXgDsrTelemetryId
    MAX-ACCESS  not-accessible
    STATUS      current
    DESCRIPTION
            "ID number of the telemetry value to use for the threshold."
    ::= { eagleXgDsrTelemetryThreshEntry 1 }

eagleXgDsrTelemetryThreshFunction  OBJECT-TYPE
    SYNTAX      EagleXgDsrTelemetryName
    MAX-ACCESS  not-accessible
    STATUS      current
    DESCRIPTION
            "The function name associated with this threshold. The function
            name appears in the instance field of any alarms raised when a
            threshold is exceeded."
    ::= { eagleXgDsrTelemetryThreshEntry 2 }

eagleXgDsrTelemetryThreshBasis  OBJECT-TYPE
    SYNTAX      EagleXgDsrTelemetryBasis
    MAX-ACCESS  read-only
    STATUS      current
    DESCRIPTION
            "Contains the basis of the threshold -- whether the threshold is
            based upon the current or running average of the telemetry value."
    ::= { eagleXgDsrTelemetryThreshEntry 3 }

eagleXgDsrTelemetryThreshAlarm  OBJECT-TYPE
    SYNTAX      EagleXgDsrAlarmNumber
    MAX-ACCESS  read-only
    STATUS      current
    DESCRIPTION
            "ID number of an alarm or event that will be used to raise an alarm
            or log an event when the threshold is exceeded. A value of -1
            disables alarming."
    ::= { eagleXgDsrTelemetryThreshEntry 7 }

eagleXgDsrTelemetryThreshSeverity OBJECT-TYPE
    SYNTAX      EagleXgDsrAlarmSeverity
    MAX-ACCESS  not-accessible
    STATUS      current
    DESCRIPTION
            "Severity of the alarm or event raised when the threshold is
            exceeded."
    ::= { eagleXgDsrTelemetryThreshEntry 8 }

eagleXgDsrTelemetryThreshSetThreshold  OBJECT-TYPE
    SYNTAX      Unsigned32
    MAX-ACCESS  read-only
    STATUS      current
    DESCRIPTION
            "Threshold value that when reached will cause the threshold to be
            exceeded."
    ::= { eagleXgDsrTelemetryThreshEntry 9 }

eagleXgDsrTelemetryThreshClearThreshold  OBJECT-TYPE
    SYNTAX      Unsigned32
    MAX-ACCESS  read-only
    STATUS      current
    DESCRIPTION
            "Value that determines when the threshold abatement is reached."
    ::= { eagleXgDsrTelemetryThreshEntry 10 }

eagleXgDsrTelemetryThreshAbateTimeMs  OBJECT-TYPE
    SYNTAX      Unsigned32
    MAX-ACCESS  read-only
    STATUS      current
    DESCRIPTION
            "How long, in seconds, a given telemetry value must remain below
            the clear threshold before the threshold is considered abated."
    ::= { eagleXgDsrTelemetryThreshEntry 11 }

eagleXgDsrTelemetryTable OBJECT-TYPE
    SYNTAX      SEQUENCE OF EagleXgDsrTelemetryEntry
    MAX-ACCESS  not-accessible
    STATUS      current
    DESCRIPTION
            "Table containing all of the collected telemetry data."
    ::= { eagleXgDsrTelemetry 4 }

eagleXgDsrTelemetryEntry OBJECT-TYPE
    SYNTAX      EagleXgDsrTelemetryEntry
    MAX-ACCESS  not-accessible
    STATUS      current
    DESCRIPTION
            "A single telemetry value indexed by part (local or merged), source
            node ID, telemetry ID and telemetry sub ID (for arrayed telemetry
            values."
    INDEX { eagleXgDsrTelemetryPart, eagleXgDsrTelemetrySrcNode, eagleXgDsrTelemetryId,
            eagleXgDsrTelemetrySubId }
    ::= { eagleXgDsrTelemetryTable 1 }

EagleXgDsrTelemetryEntry ::=
    SEQUENCE {
        eagleXgDsrTelemetryPart         EagleXgDsrMergePartNum,
        eagleXgDsrTelemetrySrcNode      EagleXgDsrNodeId,
        eagleXgDsrTelemetryId           EagleXgDsrTelemetryId,
        eagleXgDsrTelemetryMerged       TruthValue,
        eagleXgDsrTelemetryRawValue     Unsigned32,
        eagleXgDsrTelemetryRawAvg       Unsigned32,
        eagleXgDsrTelemetryUpdateTime   EagleXgDsrDateAndTime,
        eagleXgDsrTelemetryThreshInfo   OCTET STRING,
        eagleXgDsrTelemetrySubId        Integer32,
        eagleXgDsrTelemetryName         EagleXgDsrTelemetryName
    }

eagleXgDsrTelemetryPart  OBJECT-TYPE
    SYNTAX      EagleXgDsrMergePartNum
    MAX-ACCESS  not-accessible
    STATUS      current
    DESCRIPTION
            "Part number that identifies whether the telemetry value is a local
            value or a merged value."
    ::= { eagleXgDsrTelemetryEntry 1 }

eagleXgDsrTelemetrySrcNode  OBJECT-TYPE
    SYNTAX      EagleXgDsrNodeId
    MAX-ACCESS  not-accessible
    STATUS      current
    DESCRIPTION
            "Source node ID of the server originating the telemetry value. See
            the eagleXgDsrNodeInfo table for details. The source node is always all
            zeros for a local telemetry value and set to a valid node ID from
            the eagleXgDsrNodeInfo table for merged telemetry values."
    ::= { eagleXgDsrTelemetryEntry 2 }

eagleXgDsrTelemetryId  OBJECT-TYPE
    SYNTAX      EagleXgDsrTelemetryId
    MAX-ACCESS  not-accessible
    STATUS      current
    DESCRIPTION
            "Unique ID number of the telemetry value."
    ::= { eagleXgDsrTelemetryEntry 3 }

eagleXgDsrTelemetryMerged  OBJECT-TYPE
    SYNTAX      TruthValue
    MAX-ACCESS  read-only
    STATUS      current
    DESCRIPTION
            "Boolean controlling whether the telemetry value is merged or not."
    ::= { eagleXgDsrTelemetryEntry 4 }

eagleXgDsrTelemetryRawValue  OBJECT-TYPE
    SYNTAX      Unsigned32
    MAX-ACCESS  read-only
    STATUS      current
    DESCRIPTION
            "Raw unscaled numeric telemetry value."
    ::= { eagleXgDsrTelemetryEntry 5 }

eagleXgDsrTelemetryRawAvg  OBJECT-TYPE
    SYNTAX      Unsigned32
    MAX-ACCESS  read-only
    STATUS      current
    DESCRIPTION
            "Raw average numeric telemetry value."
    ::= { eagleXgDsrTelemetryEntry 6 }

eagleXgDsrTelemetryUpdateTime  OBJECT-TYPE
    SYNTAX      EagleXgDsrDateAndTime
    MAX-ACCESS  read-only
    STATUS      current
    DESCRIPTION
            "Timestamp containing the last time that this specific telemetry
            value was updated."
    ::= { eagleXgDsrTelemetryEntry 7 }

eagleXgDsrTelemetryThreshInfo  OBJECT-TYPE
    SYNTAX      OCTET STRING
    MAX-ACCESS  read-only
    STATUS      current
    DESCRIPTION
            "Information string showing whether any thresholds are currently
            exceeded."
    ::= { eagleXgDsrTelemetryEntry 8 }

eagleXgDsrTelemetrySubId  OBJECT-TYPE
    SYNTAX      Integer32 (0..2147483647)
    MAX-ACCESS  read-only
    STATUS      current
    DESCRIPTION
            "For arrayed telemetry values, this contains the sub ID."
    ::= { eagleXgDsrTelemetryEntry 9 }

eagleXgDsrTelemetryName  OBJECT-TYPE
    SYNTAX      EagleXgDsrTelemetryName
    MAX-ACCESS  read-only
    STATUS      current
    DESCRIPTION
            "Telemetry value name with expanded sub ID."
    ::= { eagleXgDsrTelemetryEntry 10 }


eagleXgDsrResynchObjects       OBJECT IDENTIFIER ::= { eagleXgDsrMIBObjects 5 }

eagleXgDsrResynchSrcNode OBJECT-TYPE
    SYNTAX      EagleXgDsrNodeId
    MAX-ACCESS  read-only
    STATUS      current
    DESCRIPTION
            "The notification source node."
    ::= { eagleXgDsrResynchObjects 1 }

eagleXgDsrResynchSrcHostname OBJECT-TYPE
    SYNTAX      DisplayString
    MAX-ACCESS  read-only
    STATUS      current
    DESCRIPTION
            "The notification source node's hostname."
    ::= { eagleXgDsrResynchObjects 2 }

eagleXgDsrResynchActiveNode OBJECT-TYPE
    SYNTAX      EagleXgDsrNodeId
    MAX-ACCESS  read-only
    STATUS      current
    DESCRIPTION
            "The notification Active node."
    ::= { eagleXgDsrResynchObjects 3 }

eagleXgDsrResynchActiveHostname OBJECT-TYPE
    SYNTAX      DisplayString
    MAX-ACCESS  read-only
    STATUS      current
    DESCRIPTION
            "The notification Active node's hostname."
    ::= { eagleXgDsrResynchObjects 4 }

eagleXgDsrResynchManagedObject OBJECT-TYPE
    SYNTAX      OBJECT IDENTIFIER
    MAX-ACCESS  read-only
    STATUS      current
    DESCRIPTION
            "The notification's managed object id."
    ::= { eagleXgDsrResynchObjects 5 }

eagleXgDsrResynchAdditionalInfo OBJECT-TYPE
    SYNTAX      DisplayString
    MAX-ACCESS  read-only
    STATUS      current
    DESCRIPTION
            "Comma-separated triplets of key flag, name and value."
    ::= { eagleXgDsrResynchObjects 6 }


eagleXgDsrResynchNotifications OBJECT IDENTIFIER ::= { eagleXgDsrMIB 3 }

eagleXgDsrToActiveFailover NOTIFICATION-TYPE
    OBJECTS {
        eagleXgDsrAlarmSequence,
        eagleXgDsrResynchSrcNode,
        eagleXgDsrResynchSrcHostname,
        eagleXgDsrResynchManagedObject,
        eagleXgDsrResynchAdditionalInfo
    }
    STATUS current
    DESCRIPTION
        "Notifies that HA failover caused the server role change 
        to Active for policy 0"
    ::= { eagleXgDsrResynchNotifications 1 }

eagleXgDsrFromActiveFailover NOTIFICATION-TYPE
    OBJECTS {
        eagleXgDsrAlarmSequence,
        eagleXgDsrResynchSrcNode,
        eagleXgDsrResynchSrcHostname,
        eagleXgDsrResynchActiveNode,
        eagleXgDsrResynchActiveHostname,
        eagleXgDsrResynchManagedObject,
        eagleXgDsrResynchAdditionalInfo
    }
    STATUS current
    DESCRIPTION
        "Notifies that HA failover caused the server role change 
        from Active to a different state for policy 0"
    ::= { eagleXgDsrResynchNotifications 2 }


tklcNbiResynchRecommended NOTIFICATION-TYPE
    OBJECTS {
        eagleXgDsrAlarmSequence,
        eagleXgDsrResynchSrcNode,
        eagleXgDsrResynchSrcHostname,
        eagleXgDsrResynchManagedObject,
        eagleXgDsrResynchAdditionalInfo
    }
    STATUS current
    DESCRIPTION
        "Notifies that resynchronization of alarm table is recommended"
    ::= { eagleXgDsrResynchNotifications 3 }


eagleXgDsrMIBNotifications  OBJECT IDENTIFIER ::= { eagleXgDsrMIB 2 }


eagleXgDsrSwFaultNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Program impaired by s/w fault"
    ::= { eagleXgDsrMIBNotifications 31000 }
        

eagleXgDsrSwStatusNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Program status"
    ::= { eagleXgDsrMIBNotifications 31001 }
        

eagleXgDsrProcWatchdogFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Process watchdog timed out"
    ::= { eagleXgDsrMIBNotifications 31002 }
        

eagleXgDsrThreadWatchdogFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Thread watchdog timed out"
    ::= { eagleXgDsrMIBNotifications 31003 }
        

eagleXgDsrTestStatNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "For testing purposes only"
    ::= { eagleXgDsrMIBNotifications 31004 }
        

eagleXgDsrTestFaultNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "For testing purposes only"
    ::= { eagleXgDsrMIBNotifications 31005 }
        

eagleXgDsrDbReplicationFaultNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The DB replication process is impaired by a s/w fault"
    ::= { eagleXgDsrMIBNotifications 31100 }
        

eagleXgDsrDbRepToSlaveFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DB replication to a slave DB has failed"
    ::= { eagleXgDsrMIBNotifications 31101 }
        

eagleXgDsrDbRepFromMasterFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DB replication from a master DB has failed"
    ::= { eagleXgDsrMIBNotifications 31102 }
        

eagleXgDsrDbRepUpdateFaultNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DB Replication process cannot apply update to DB"
    ::= { eagleXgDsrMIBNotifications 31103 }
        

eagleXgDsrDbRepLatencyNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DB Replication latency has exceeded thresholds"
    ::= { eagleXgDsrMIBNotifications 31104 }
        

eagleXgDsrDbMergeFaultNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The DB merge process (inetmerge) is impaired by a s/w fault"
    ::= { eagleXgDsrMIBNotifications 31105 }
        

eagleXgDsrDbMergeToParentFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DB merging to the parent Merge Node has failed"
    ::= { eagleXgDsrMIBNotifications 31106 }
        

eagleXgDsrDbMergeFromChildFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DB merging from a child Source Node has failed"
    ::= { eagleXgDsrMIBNotifications 31107 }
        

eagleXgDsrDbMergeLatencyNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DB Merge latency has exceeded thresholds"
    ::= { eagleXgDsrMIBNotifications 31108 }
        

eagleXgDsrTopErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Topology is configured incorrectly"
    ::= { eagleXgDsrMIBNotifications 31109 }
        

eagleXgDsrDbAuditFaultNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The DB audit process (iaudit) is impaired by a s/w fault"
    ::= { eagleXgDsrMIBNotifications 31110 }
        

eagleXgDsrDbMergeAuditNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DB Merge Audit between mate nodes in progress"
    ::= { eagleXgDsrMIBNotifications 31111 }
        

eagleXgDsrDbRepUpLogTransTimeoutNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DB Replicated data may not have transferred in the time allotted."
    ::= { eagleXgDsrMIBNotifications 31112 }
        

eagleXgDsrDbReplicationManuallyDisabledNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Replication Manually Disabled"
    ::= { eagleXgDsrMIBNotifications 31113 }
        

eagleXgDsrDbReplicationSoapFaultNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DB Replication of configuration data via SOAP has failed"
    ::= { eagleXgDsrMIBNotifications 31114 }
        

eagleXgDsrDbServiceFaultNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The DB service process (idbsvc) is impaired by a s/w fault"
    ::= { eagleXgDsrMIBNotifications 31115 }
        

eagleXgDsrExcessiveSharedMemoryConsumptionNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The amount of shared memory consumed exceeds configured thresholds"
    ::= { eagleXgDsrMIBNotifications 31116 }
        

eagleXgDsrLowDiskFreeNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The amount of free disk is below configured thresholds"
    ::= { eagleXgDsrMIBNotifications 31117 }
        

eagleXgDsrDbDiskStoreFaultNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Writing the database to disk failed"
    ::= { eagleXgDsrMIBNotifications 31118 }
        

eagleXgDsrDbUpdateLogOverrunNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The DB update log was overrun increasing risk of data loss"
    ::= { eagleXgDsrMIBNotifications 31119 }
        

eagleXgDsrDbUpdateLogWriteFaultNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "A DB change cannot be stored in the updatelog"
    ::= { eagleXgDsrMIBNotifications 31120 }
        

eagleXgDsrLowDiskFreeEarlyWarningNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The amount of free disk is below configured early warning thresholds"
    ::= { eagleXgDsrMIBNotifications 31121 }
        

eagleXgDsrExcessiveShMemConsumptionEarlyWarnNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The amount of shared memory consumed exceeds configured early warning thresholds"
    ::= { eagleXgDsrMIBNotifications 31122 }
        

eagleXgDsrDbRepAuditCmdCompleteNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "ADIC completed successfully"
    ::= { eagleXgDsrMIBNotifications 31123 }
        

eagleXgDsrDbRepAuditCmdErrNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "An ADIC detected errors"
    ::= { eagleXgDsrMIBNotifications 31124 }
        

eagleXgDsrDbDurabilityDegradedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DB durability has dropped below configured durability level"
    ::= { eagleXgDsrMIBNotifications 31125 }
        

eagleXgDsrAuditBlockedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Site Audit Controls blocked an inter-site replication audit due to the number in progress per configuration"
    ::= { eagleXgDsrMIBNotifications 31126 }
        

eagleXgDsrDbRepAuditCompleteNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DB replication audit completed"
    ::= { eagleXgDsrMIBNotifications 31127 }
        

eagleXgDsrDbADICErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "ADIC found one or more errors that are not automatically fixable."
    ::= { eagleXgDsrMIBNotifications 31128 }
        

eagleXgDsrDbADICWarnNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "ADIC found one or more minor issues that can most likely be ignored."
    ::= { eagleXgDsrMIBNotifications 31129 }
        

eagleXgDsrNetworkHealthWarningNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Network health issue detected."
    ::= { eagleXgDsrMIBNotifications 31130 }
        

eagleXgDsrOustedThrottleWarnNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DB ousted throttle may be affecting processes."
    ::= { eagleXgDsrMIBNotifications 31131 }
        

eagleXgDsrDbRepPrecRelaxedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Standby Database updates are falling behind.  Relaxing the replication barrier to allow non-Standby Databases to update as fast as possible."
    ::= { eagleXgDsrMIBNotifications 31132 }
        

eagleXgDsrDbRepSwitchoverNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DB Replication Active to Standby switchover exceeded maximum swithover time."
    ::= { eagleXgDsrMIBNotifications 31133 }
        

eagleXgDsrDbSiteRepToSlaveFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DB Site replication to a slave DB has failed"
    ::= { eagleXgDsrMIBNotifications 31134 }
        

eagleXgDsrDbSiteRepFromMasterFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DB Site replication from a master DB has failed"
    ::= { eagleXgDsrMIBNotifications 31135 }
        

eagleXgDsrDbSiteRepPrecRelaxedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Standby Site Database updates are falling behind.  Relaxing the replication barrier to allow non-Standby Site Databases to update as fast as possible."
    ::= { eagleXgDsrMIBNotifications 31136 }
        

eagleXgDsrDbSiteRepLatencyNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DB Site Replication latency has exceeded thresholds"
    ::= { eagleXgDsrMIBNotifications 31137 }
        

eagleXgDsrDbPerlFaultNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Perl interface to DB is impaired by a s/w fault"
    ::= { eagleXgDsrMIBNotifications 31140 }
        

eagleXgDsrDbSQLFaultNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SQL interface to DB is impaired by a s/w fault"
    ::= { eagleXgDsrMIBNotifications 31145 }
        

eagleXgDsrDbMastershipFaultNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DB replication is impaired due to no mastering process (inetrep)"
    ::= { eagleXgDsrMIBNotifications 31146 }
        

eagleXgDsrDbUpSyncLogOverrunNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "UpSyncLog is not big enough for (WAN) replication"
    ::= { eagleXgDsrMIBNotifications 31147 }
        

eagleXgDsrDbLockErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DB lock integrity error detected"
    ::= { eagleXgDsrMIBNotifications 31148 }
        

eagleXgDsrDbLateWriteNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Application wrote to database while HA role change from active was in progress"
    ::= { eagleXgDsrMIBNotifications 31149 }
        

eagleXgDsrDbHealthImpactNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Database health impacted"
    ::= { eagleXgDsrMIBNotifications 31150 }
        

eagleXgDsrDbHealthImpactPersistNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Persistent database failure "
    ::= { eagleXgDsrMIBNotifications 31151 }
        

eagleXgDsrProcMgmtFaultNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The process manager (procmgr) is impaired by a s/w fault"
    ::= { eagleXgDsrMIBNotifications 31200 }
        

eagleXgDsrProcNotRunningNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "A managed process cannot be started or has unexpectedly terminated"
    ::= { eagleXgDsrMIBNotifications 31201 }
        

eagleXgDsrProcZombieProcessNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "A zombie process exists that cannot be killed by procmgr.  procmgr will no longer manage this process.  If the process does not exit, it may be necessary to reboot the server to eliminate the zombie process."
    ::= { eagleXgDsrMIBNotifications 31202 }
        

eagleXgDsrProcMgmtMonFaultNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The process manager monitor (pm.watchdog) is impaired by a s/w fault"
    ::= { eagleXgDsrMIBNotifications 31206 }
        

eagleXgDsrProcResourceMonFaultNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The process resource monitor (ProcWatch) is impaired by a s/w fault"
    ::= { eagleXgDsrMIBNotifications 31207 }
        

eagleXgDsrPortServerFaultNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The run environment port mapper (re.portmap) is impaired by a s/w fault"
    ::= { eagleXgDsrMIBNotifications 31208 }
        

eagleXgDsrHostLookupFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Unable to resolve a hostname specified in the NodeInfo table."
    ::= { eagleXgDsrMIBNotifications 31209 }
        

eagleXgDsrProcSchedulerFaultNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The process scheduler (ProcSched/runat) is impaired by a s/w fault"
    ::= { eagleXgDsrMIBNotifications 31213 }
        

eagleXgDsrScheduleProcessFaultNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "A scheduled process cannot be executed or abnormally terminated"
    ::= { eagleXgDsrMIBNotifications 31214 }
        

eagleXgDsrProcResourcesExceededFaultNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "A process is consuming excessive system resources"
    ::= { eagleXgDsrMIBNotifications 31215 }
        

eagleXgDsrSysMetricConfigErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "A SysMetric configuration table contains invalid data"
    ::= { eagleXgDsrMIBNotifications 31216 }
        

eagleXgDsrNetworkUnreachableWarningNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Unreachable Network Detected"
    ::= { eagleXgDsrMIBNotifications 31217 }
        

eagleXgDsrHaCfgMonitorFaultNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  obsolete
    DESCRIPTION
            "The HA manager (cmha) is impaired by a s/w fault"
    ::= { eagleXgDsrMIBNotifications 31220 }
        

eagleXgDsrHaAlarmMonitorFaultNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  obsolete
    DESCRIPTION
            "The high availability alarm monitor is impaired by a s/w fault"
    ::= { eagleXgDsrMIBNotifications 31221 }
        

eagleXgDsrHaNotConfiguredNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  obsolete
    DESCRIPTION
            "High availability is disabled due to system configuration"
    ::= { eagleXgDsrMIBNotifications 31222 }
        

eagleXgDsrHaHbTransmitFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  obsolete
    DESCRIPTION
            "The high availability monitor failed to send heartbeat"
    ::= { eagleXgDsrMIBNotifications 31223 }
        

eagleXgDsrHaCfgErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "High availability configuration error"
    ::= { eagleXgDsrMIBNotifications 31224 }
        

eagleXgDsrHaSvcStartFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The required high availability resource failed to start"
    ::= { eagleXgDsrMIBNotifications 31225 }
        

eagleXgDsrHaAvailDegradedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The high availability status is degraded due to raised alarms"
    ::= { eagleXgDsrMIBNotifications 31226 }
        

eagleXgDsrHaAvailFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The high availability status is failed due to raised alarms"
    ::= { eagleXgDsrMIBNotifications 31227 }
        

eagleXgDsrHaStandbyOfflineNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  obsolete
    DESCRIPTION
            "HA Standby Server Offline"
    ::= { eagleXgDsrMIBNotifications 31228 }
        

eagleXgDsrHaScoreChangeNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "High availability health score changed"
    ::= { eagleXgDsrMIBNotifications 31229 }
        

eagleXgDsrHaLateHeartbeatWarningNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "High availability server has not received a message on specified path within the configured interval"
    ::= { eagleXgDsrMIBNotifications 31232 }
        

eagleXgDsrHaPathDownNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "High availability path loss of connectivity"
    ::= { eagleXgDsrMIBNotifications 31233 }
        

eagleXgDsrHaLinkDownNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "High availability TCP link is down"
    ::= { eagleXgDsrMIBNotifications 31236 }
        

eagleXgDsrRecAlarmEvProcFaultNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The recent alarm event manager (raclerk) is impaired by a s/w fault"
    ::= { eagleXgDsrMIBNotifications 31230 }
        

eagleXgDsrPlatAlarmAgentNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The platform alarm agent impaired by a s/w fault"
    ::= { eagleXgDsrMIBNotifications 31231 }
        

eagleXgDsrUtrustedTimeOnInitNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Upon system initialization, the system time is not trusted probably because NTP is misconfigured or the NTP servers are unreachable.  There are often accompanying Platform alarms to guide correction.  Generally, applications are not started if time is not believed to be correct on start-up. Recovery will often will require rebooting the server."
    ::= { eagleXgDsrMIBNotifications 31234 }
        

eagleXgDsrUtrustedTimePostInitNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "After system initialization, the system time has become untrusted probably because NTP has reconfigured improperly, time has been manually changed, the NTP servers are unreachable, etc.  There are often accompanying Platform alarms to guide correction.  Generally, applications remaining be running, but time-stamped data is likely incorrect, reports may be negatively affected, some behavior may be improper, etc."
    ::= { eagleXgDsrMIBNotifications 31235 }
        

eagleXgDsrMeasCollectorFaultNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The measurements collector (statclerk) is impaired by a s/w fault"
    ::= { eagleXgDsrMIBNotifications 31240 }
        

eagleXgDsrRePortMappingFaultNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The IP service port mapper (re.portmap) is impaired by a s/w fault"
    ::= { eagleXgDsrMIBNotifications 31250 }
        

eagleXgDsrSnmpAgentNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The SNMP agent (cmsnmpa) is impaired by a s/w fault"
    ::= { eagleXgDsrMIBNotifications 31260 }
        

eagleXgDsrSnmpConfigNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "A SNMP configuration error was detected"
    ::= { eagleXgDsrMIBNotifications 31261 }
        

eagleXgDsrLoggingOutputNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Logging Output set to Above Normal"
    ::= { eagleXgDsrMIBNotifications 31270 }
        

eagleXgDsrActiveToStandbyTransNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  obsolete
    DESCRIPTION
            "HA active to standby activity transition"
    ::= { eagleXgDsrMIBNotifications 31280 }
        

eagleXgDsrStandbyToActiveTransNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  obsolete
    DESCRIPTION
            "HA standby to active activity transition"
    ::= { eagleXgDsrMIBNotifications 31281 }
        

eagleXgDsrHaMgmtFaultNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The HA manager (cmha) is impaired by a s/w fault"
    ::= { eagleXgDsrMIBNotifications 31282 }
        

eagleXgDsrHaServerOfflineNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "High availability server is offline"
    ::= { eagleXgDsrMIBNotifications 31283 }
        

eagleXgDsrHaRemoteHeartbeatWarningNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "High availability remote subscriber has not received a heartbeat within the configured interval"
    ::= { eagleXgDsrMIBNotifications 31284 }
        

eagleXgDsrHaSbrEntryNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "High availability node join recovery entered "
    ::= { eagleXgDsrMIBNotifications 31285 }
        

eagleXgDsrHaSbrPlanNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "High availability node join recovery plan "
    ::= { eagleXgDsrMIBNotifications 31286 }
        

eagleXgDsrHaSbrCompleteNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "High availability node join recovery complete "
    ::= { eagleXgDsrMIBNotifications 31287 }
        

eagleXgDsrHaBadSiteCfgNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "High availability site configuration error"
    ::= { eagleXgDsrMIBNotifications 31288 }
        


eagleXgDsrHaProcessStatusNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "HA manager (cmha) status"
    ::= { eagleXgDsrMIBNotifications 31290 }
        

eagleXgDsrHaElectionStatusNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "HA DC Election status"
    ::= { eagleXgDsrMIBNotifications 31291 }
        

eagleXgDsrHaPolicyStatusNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "HA Policy plan status"
    ::= { eagleXgDsrMIBNotifications 31292 }
        

eagleXgDsrHaRaLinkStatusNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "HA Resource Agent Link status"
    ::= { eagleXgDsrMIBNotifications 31293 }
        

eagleXgDsrHaResourceStatusNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "HA Resource registration status"
    ::= { eagleXgDsrMIBNotifications 31294 }
        

eagleXgDsrHaActionStatusNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "HA Resource action status"
    ::= { eagleXgDsrMIBNotifications 31295 }
        

eagleXgDsrHaMonitorStatusNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "HA Monitor action status"
    ::= { eagleXgDsrMIBNotifications 31296 }
        

eagleXgDsrHaRaInfoNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "HA Resource Agent application information"
    ::= { eagleXgDsrMIBNotifications 31297 }
        

eagleXgDsrHaRaDetailNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "HA Resource Agent application detailed information"
    ::= { eagleXgDsrMIBNotifications 31298 }
        

eagleXgDsrHaNotificationNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "HA Notification status"
    ::= { eagleXgDsrMIBNotifications 31299 }
        

eagleXgDsrHaControlNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "HA Control action status"
    ::= { eagleXgDsrMIBNotifications 31300 }
        

eagleXgDsrHaTopologyNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "HA Topology Events"
    ::= { eagleXgDsrMIBNotifications 31301 }
        

eagleXgDsrHaBadCfgNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "High availability configuration error"
    ::= { eagleXgDsrMIBNotifications 31322 }
        

eagleXgDsrTpdBrkPnlFeedUnavailableNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Breaker Panel Feed Unavailable"
    ::= { eagleXgDsrMIBNotifications 32100 }


eagleXgDsrTpdBrkPnlBreakerFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Breaker Panel Breaker Failure"
    ::= { eagleXgDsrMIBNotifications 32101 }


eagleXgDsrTpdBrkPnlMntFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Breaker Panel Monitoring Failure"
    ::= { eagleXgDsrMIBNotifications 32102 }


eagleXgDsrTpdPowerFeedUnavailNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Power Feed Unavailable"
    ::= { eagleXgDsrMIBNotifications 32103 }


eagleXgDsrTpdPowerSupply1FailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Power Supply 1 Failure - deprecated"
    ::= { eagleXgDsrMIBNotifications 32104 }


eagleXgDsrTpdPowerSupply2FailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Power Supply 2 Failure - deprecated"
    ::= { eagleXgDsrMIBNotifications 32105 }


eagleXgDsrTpdPowerSupply3FailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Power Supply 3 Failure - deprecated"
    ::= { eagleXgDsrMIBNotifications 32106 }


eagleXgDsrTpdRaidFeedUnavailableNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "RAID Feed Unavailable"
    ::= { eagleXgDsrMIBNotifications 32107 }


eagleXgDsrTpdRaidPower1FailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "RAID Power Supply 1 Failure"
    ::= { eagleXgDsrMIBNotifications 32108 }


eagleXgDsrTpdRaidPower2FailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "RAID Power Supply 2 Failure"
    ::= { eagleXgDsrMIBNotifications 32109 }


eagleXgDsrTpdRaidPower3FailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "RAID Power Supply 3 Failure"
    ::= { eagleXgDsrMIBNotifications 32110 }


eagleXgDsrTpdDeviceFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Device Failure"
    ::= { eagleXgDsrMIBNotifications 32111 }


eagleXgDsrTpdDeviceIfFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Device Interface Failure"
    ::= { eagleXgDsrMIBNotifications 32112 }


eagleXgDsrTpdEccUncorrectableErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Uncorrectable ECC Memory Error"
    ::= { eagleXgDsrMIBNotifications 32113 }


eagleXgDsrTpdSNMPGetFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SNMP Get Failure"
    ::= { eagleXgDsrMIBNotifications 32114 }


eagleXgDsrTpdChronyDaemonNotSynchronizedFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Chrony Daemon Lost Synchronization For Extended Time"
    ::= { eagleXgDsrMIBNotifications 32115 }


eagleXgDsrTpdNTPTimeGoneBackwardsNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server's Time Has Gone Backwards"
    ::= { eagleXgDsrMIBNotifications 32116 }


eagleXgDsrNtpOffsetCheckFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "NTP Offset Check Failure"
    ::= { eagleXgDsrMIBNotifications 32117 }


eagleXgDsrTpdFanErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Fan Failure. This test uses the leaky bucket algorithm."
    ::= { eagleXgDsrMIBNotifications 32300 }


eagleXgDsrTpdIntDiskErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Internal Disk Error"
    ::= { eagleXgDsrMIBNotifications 32301 }


eagleXgDsrTpdRaidDiskErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server RAID Disk Error"
    ::= { eagleXgDsrMIBNotifications 32302 }


eagleXgDsrTpdPlatformErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Platform Error"
    ::= { eagleXgDsrMIBNotifications 32303 }


eagleXgDsrTpdFileSystemErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server File System Error"
    ::= { eagleXgDsrMIBNotifications 32304 }


eagleXgDsrTpdPlatProcessErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Platform Process Error"
    ::= { eagleXgDsrMIBNotifications 32305 }


eagleXgDsrTpdRamShortageErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server RAM Shortage Error. This test uses the leaky bucket algorithm."
    ::= { eagleXgDsrMIBNotifications 32306 }


eagleXgDsrTpdSwapSpaceShortageErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Swap Space Shortage Error. This test uses the leaky bucket algorithm."
    ::= { eagleXgDsrMIBNotifications 32307 }


eagleXgDsrTpdProvNetworkErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Provisioning Network Error"
    ::= { eagleXgDsrMIBNotifications 32308 }


eagleXgDsrTpdEagleNetworkAErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Eagle Network A Error"
    ::= { eagleXgDsrMIBNotifications 32309 }


eagleXgDsrTpdEagleNetworkBErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Eagle Network B Error"
    ::= { eagleXgDsrMIBNotifications 32310 }


eagleXgDsrTpdSyncNetworkErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Sync Network Error"
    ::= { eagleXgDsrMIBNotifications 32311 }


eagleXgDsrTpdDiskSpaceShortageErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Disk Space Shortage Error"
    ::= { eagleXgDsrMIBNotifications 32312 }


eagleXgDsrTpdDefaultRouteNetworkErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Default Route Network Error"
    ::= { eagleXgDsrMIBNotifications 32313 }


eagleXgDsrTpdTemperatureErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Temperature Error"
    ::= { eagleXgDsrMIBNotifications 32314 }


eagleXgDsrTpdMainboardVoltageErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Mainboard Voltage Error"
    ::= { eagleXgDsrMIBNotifications 32315 }


eagleXgDsrTpdPowerFeedErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Power Feed Error"
    ::= { eagleXgDsrMIBNotifications 32316 }


eagleXgDsrTpdDiskHealthErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Disk Health Test Error"
    ::= { eagleXgDsrMIBNotifications 32317 }


eagleXgDsrTpdDiskUnavailableErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Disk Unavailable Error"
    ::= { eagleXgDsrMIBNotifications 32318 }


eagleXgDsrTpdDeviceErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Device Error"
    ::= { eagleXgDsrMIBNotifications 32319 }


eagleXgDsrTpdDeviceIfErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Device Interface Error"
    ::= { eagleXgDsrMIBNotifications 32320 }


eagleXgDsrTpdEccCorrectableErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Correctable ECC Memory Error"
    ::= { eagleXgDsrMIBNotifications 32321 }


eagleXgDsrTpdPowerSupply1ErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Power Supply A Error"
    ::= { eagleXgDsrMIBNotifications 32322 }


eagleXgDsrTpdPowerSupply2ErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Power Supply B Error"
    ::= { eagleXgDsrMIBNotifications 32323 }


eagleXgDsrTpdBrkPnlFeedErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Breaker Panel Feed Error"
    ::= { eagleXgDsrMIBNotifications 32324 }


eagleXgDsrTpdBrkPnlBreakerErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Breaker Panel Breaker Error"
    ::= { eagleXgDsrMIBNotifications 32325 }


eagleXgDsrTpdBrkPnlMntErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Breaker Panel Monitoring Error"
    ::= { eagleXgDsrMIBNotifications 32326 }


eagleXgDsrTpdHaKeepaliveErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server HA Keepalive Error"
    ::= { eagleXgDsrMIBNotifications 32327 }


eagleXgDsrTpdDrbdUnavailableNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DRBD block device can not be mounted."
    ::= { eagleXgDsrMIBNotifications 32328 }


eagleXgDsrTpdDrbdNotReplicatingNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DRBD block device is not being replicated to peer."
    ::= { eagleXgDsrMIBNotifications 32329 }


eagleXgDsrTpdDrbdPeerProblemNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DRBD peer needs intervention."
    ::= { eagleXgDsrMIBNotifications 32330 }


eagleXgDsrTpdHpDiskProblemNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "HP Disks need intervention."
    ::= { eagleXgDsrMIBNotifications 32331 }


eagleXgDsrTpdHpDiskCtrlrProblemNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "HP Smart Array controller needs intervention."
    ::= { eagleXgDsrMIBNotifications 32332 }


eagleXgDsrTpdHPACUCLIProblemNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The hpacucliStatus utility needs intervention."
    ::= { eagleXgDsrMIBNotifications 32333 }


eagleXgDsrTpdMpathDeviceProblemNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Multipath device access link needs intervention."
    ::= { eagleXgDsrMIBNotifications 32334 }


eagleXgDsrTpdSwitchLinkDownErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Switch Link Down Error"
    ::= { eagleXgDsrMIBNotifications 32335 }


eagleXgDsrTpdHalfOpenSockLimitNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Half open TCP sockets limit reached"
    ::= { eagleXgDsrMIBNotifications 32336 }


eagleXgDsrTpdFlashProgramFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Flash device failed to update"
    ::= { eagleXgDsrMIBNotifications 32337 }


eagleXgDsrTpdSerialMezzUnseatedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Serial Mezzanine card is not seated properly"
    ::= { eagleXgDsrMIBNotifications 32338 }


eagleXgDsrTpdMaxPidLimitNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Max number running of proccesss limit reached"
    ::= { eagleXgDsrMIBNotifications 32339 }


eagleXgDsrTpdChronyDaemonNotSynchronizedErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Chrony Daemon Lost Synchronization For Extended Time"
    ::= { eagleXgDsrMIBNotifications 32340 }


eagleXgDsrTpdChronyDaemonNeverSynchronizedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Chrony Daemon Never Synchronized"
    ::= { eagleXgDsrMIBNotifications 32341 }


eagleXgDsrNtpOffsetCheckErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "NTP Offset Check Failure"
    ::= { eagleXgDsrMIBNotifications 32342 }


eagleXgDsrTpdDiskProblemNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "RAID disk member(s) need intervention."
    ::= { eagleXgDsrMIBNotifications 32343 }


eagleXgDsrTpdDiskCtrlrProblemNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "RAID controller needs intervention."
    ::= { eagleXgDsrMIBNotifications 32344 }


eagleXgDsrTpdUpgradeSnapshotInvalidNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "LVM snapshot is invalid"
    ::= { eagleXgDsrMIBNotifications 32345 }


eagleXgDsrTpdOEMHardwareProblemNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "OEM hardware management service reports an error"
    ::= { eagleXgDsrMIBNotifications 32346 }


eagleXgDsrTpdHWMGMTCLIProblemNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The hwmgmtcliStatus daemon needs intervention"
    ::= { eagleXgDsrMIBNotifications 32347 }


eagleXgDsrTpdFipsSubsystemProblemNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The FIPS subsystem needs intervention"
    ::= { eagleXgDsrMIBNotifications 32348 }


eagleXgDsrTpdHidsFileTamperingNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "HIDS has detected file tampering"
    ::= { eagleXgDsrMIBNotifications 32349 }


eagleXgDsrTpdSecurityProcessDownNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "HIDS detected security process is down"
    ::= { eagleXgDsrMIBNotifications 32350 }


eagleXgDsrTpdDiskSpaceShortageWarningNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Disk Space Shortage Warning"
    ::= { eagleXgDsrMIBNotifications 32500 }


eagleXgDsrTpdApplicationProcessErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Application Process Error"
    ::= { eagleXgDsrMIBNotifications 32501 }


eagleXgDsrTpdHardwareConfigErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Hardware Configuration Error"
    ::= { eagleXgDsrMIBNotifications 32502 }


eagleXgDsrTpdRamShortageWarningNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server RAM Shortage Warning. This test uses the leaky bucket algorithm."
    ::= { eagleXgDsrMIBNotifications 32503 }


eagleXgDsrTpdSoftwareConfigErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Software Configuration Error"
    ::= { eagleXgDsrMIBNotifications 32504 }


eagleXgDsrTpdSwapSpaceShortageWarningNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Swap Space Shortage Warning. This test uses the leaky bucket algorithm."
    ::= { eagleXgDsrMIBNotifications 32505 }


eagleXgDsrTpdDefaultRouteNotDefinedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Default Router not Defined"
    ::= { eagleXgDsrMIBNotifications 32506 }


eagleXgDsrTpdTemperatureWarningNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Temperature Warning"
    ::= { eagleXgDsrMIBNotifications 32507 }


eagleXgDsrTpdCoreFileDetectedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Core File Detected"
    ::= { eagleXgDsrMIBNotifications 32508 }


eagleXgDsrTpdChronyDaemonNotSynchronizedWarningNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Chrony Daemon Not Synchronized"
    ::= { eagleXgDsrMIBNotifications 32509 }


eagleXgDsrTpdCMOSBatteryVoltageLowNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "CMOS Battery Voltage Low"
    ::= { eagleXgDsrMIBNotifications 32510 }


eagleXgDsrTpdSmartTestWarnNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Disk Self Test Warning"
    ::= { eagleXgDsrMIBNotifications 32511 }


eagleXgDsrTpdDeviceWarnNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Device Warning"
    ::= { eagleXgDsrMIBNotifications 32512 }


eagleXgDsrTpdDeviceIfWarnNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Device Interface Warning"
    ::= { eagleXgDsrMIBNotifications 32513 }


eagleXgDsrTpdWatchdogRebootNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Reboot Watchdog Initiated"
    ::= { eagleXgDsrMIBNotifications 32514 }


eagleXgDsrTpdHaInhibitedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server HA Failover Inhibited"
    ::= { eagleXgDsrMIBNotifications 32515 }


eagleXgDsrTpdHaActiveToStandbyTransNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server HA Active To Standby Transition"
    ::= { eagleXgDsrMIBNotifications 32516 }


eagleXgDsrTpdHaStandbyToActiveTransNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server HA Standby To Active Transition"
    ::= { eagleXgDsrMIBNotifications 32517 }


eagleXgDsrTpdPlatformHealthCheckFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Platform Health Check Failure"
    ::= { eagleXgDsrMIBNotifications 32518 }


eagleXgDsrNtpOffsetCheckFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "NTP Offset Check Failure"
    ::= { eagleXgDsrMIBNotifications 32519 }


eagleXgDsrNtpStratumCheckFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "NTP Stratum Check Failure"
    ::= { eagleXgDsrMIBNotifications 32520 }


eagleXgDsrSasPresenceSensorMissingNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SAS Presence Sensor Missing"
    ::= { eagleXgDsrMIBNotifications 32521 }


eagleXgDsrSasDriveMissingNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SAS Drive Missing"
    ::= { eagleXgDsrMIBNotifications 32522 }


eagleXgDsrTpdDrbdFailoverBusyNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "This DRBD node is not currently ready to act as primary."
    ::= { eagleXgDsrMIBNotifications 32523 }


eagleXgDsrTpdHpDiskResyncNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "HP Disk is resyncing."
    ::= { eagleXgDsrMIBNotifications 32524 }


eagleXgDsrTpdTelcoFanWarningNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Telco Fan Warning"
    ::= { eagleXgDsrMIBNotifications 32525 }


eagleXgDsrTpdTelcoTemperatureWarningNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Telco Temperature Warning"
    ::= { eagleXgDsrMIBNotifications 32526 }


eagleXgDsrTpdTelcoPowerSupplyWarningNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Telco Power Supply Warning"
    ::= { eagleXgDsrMIBNotifications 32527 }


eagleXgDsrTpdInvalidBiosValueNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Invalid BIOS value"
    ::= { eagleXgDsrMIBNotifications 32528 }


eagleXgDsrTpdServerKernelDumpFileDetectedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Kernel Dump File Detected"
    ::= { eagleXgDsrMIBNotifications 32529 }


eagleXgDsrTpdServerUpgradeFailDetectedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Upgrade Fail Detected"
    ::= { eagleXgDsrMIBNotifications 32530 }


eagleXgDsrTpdHalfOpenSocketWarningNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Half Open TCP Sockets Warning"
    ::= { eagleXgDsrMIBNotifications 32531 }


eagleXgDsrTpdServerUpgradePendingAcceptNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Upgrade Pending Accept/Reject"
    ::= { eagleXgDsrMIBNotifications 32532 }


eagleXgDsrTpdMaxPidWarningNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Max number running of proccesss limit warning"
    ::= { eagleXgDsrMIBNotifications 32533 }


eagleXgDsrTpdNTPSourceIsBadNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "NTP Source Server Is Not Able To Provide Correct Time"
    ::= { eagleXgDsrMIBNotifications 32534 }


eagleXgDsrTpdDiskResyncNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "RAID member disk is resyncing."
    ::= { eagleXgDsrMIBNotifications 32535 }


eagleXgDsrTpdUpgradeSnapshotWarningNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "LVM snapshot space usage warning"
    ::= { eagleXgDsrMIBNotifications 32536 }


eagleXgDsrTpdFipsSubsystemWarningNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The FIPS subsystem needs intervention"
    ::= { eagleXgDsrMIBNotifications 32537 }


eagleXgDsrTpdPdcErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Platform Data Collection Error"
    ::= { eagleXgDsrMIBNotifications 32538 }


eagleXgDsrTpdServerPatchPendingAcceptNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Patch Pending Accept/Reject"
    ::= { eagleXgDsrMIBNotifications 32539 }


eagleXgDsrTpdCpuPowerLimitMismatchNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The BIOS setting for CPU Power Limit is different than expected"
    ::= { eagleXgDsrMIBNotifications 32540 }


eagleXgDsrTpdTelcoSwitchNotificationNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Telco Switch Notification"
    ::= { eagleXgDsrMIBNotifications 32700 }


eagleXgDsrTpdHidsBaselineCreatedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The TPD HIDS baseline was created"
    ::= { eagleXgDsrMIBNotifications 32701 }


eagleXgDsrTpdHidsBaselineDeletedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The TPD HIDS baseline was deleted"
    ::= { eagleXgDsrMIBNotifications 32702 }


eagleXgDsrTpdHidsEnabledNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "TPD HIDS has been enabled"
    ::= { eagleXgDsrMIBNotifications 32703 }


eagleXgDsrTpdHidsDisabledNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "TPD HIDS has been disabled"
    ::= { eagleXgDsrMIBNotifications 32704 }


eagleXgDsrTpdHidsSuspendedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "TPD HIDS monitoring has been suspended"
    ::= { eagleXgDsrMIBNotifications 32705 }


eagleXgDsrTpdHidsResumedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "TPD HIDS monitoring has been resumed"
    ::= { eagleXgDsrMIBNotifications 32706 }


eagleXgDsrTpdHidsBaselineUpdatedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "TPD HIDS baseline has been updated"
    ::= { eagleXgDsrMIBNotifications 32707 }






tekelecBackupStartNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Backup started"
    ::= { eagleXgDsrMIBNotifications 10001 }
        

tekelecBackupCompleteNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Backup completed"
    ::= { eagleXgDsrMIBNotifications 10002 }
        

tekelecBackupFailNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Backup failed"
    ::= { eagleXgDsrMIBNotifications 10003 }
        

tekelecRestoreStartNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Restoration started"
    ::= { eagleXgDsrMIBNotifications 10004 }
        

tekelecRestoreCompleteNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Restoration completed"
    ::= { eagleXgDsrMIBNotifications 10005 }
        

tekelecRestoreFailNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Restoration failed"
    ::= { eagleXgDsrMIBNotifications 10006 }
        

tekelecProvisioningManuallyDisabled NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Provisioning Manually Disabled"
    ::= { eagleXgDsrMIBNotifications 10008 }
        

oAGTCfgProvDbNoSync NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Config and Prov DB not yet synchronized"
    ::= { eagleXgDsrMIBNotifications 10009 }
        

oAGTStDbNoSync NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Stateful database not yet synchronized with mate database"
    ::= { eagleXgDsrMIBNotifications 10010 }
        

oAGTCantMonitorTable NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Monitoring for table cannot be set up"
    ::= { eagleXgDsrMIBNotifications 10011 }
        

oAGTResponderFailed NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The responder for a monitored table failed to respond to a table change"
    ::= { eagleXgDsrMIBNotifications 10012 }
        

oAGTApplSWDisabled NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Application restart in progress - see additional info (Alarms & Events -> View History) for reason"
    ::= { eagleXgDsrMIBNotifications 10013 }
        

tekelecResourceAuditFailure NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "An unexpected error occured in the execution of an external resource audit"
    ::= { eagleXgDsrMIBNotifications 10050 }
        

tekelecRouteDeploymentFailed NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "An error occured in the deployment of a network route"
    ::= { eagleXgDsrMIBNotifications 10051 }
        

tekelecRouteDiscoveryFailed NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "An error occured in the discovery of network routes"
    ::= { eagleXgDsrMIBNotifications 10052 }
        

tekelecNoRouteDevice NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Could not identify a suitable device for the deployment of a network route"
    ::= { eagleXgDsrMIBNotifications 10053 }
        

tekelecDeviceDeploymentFailed NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "An error occured in the deployment of a network device"
    ::= { eagleXgDsrMIBNotifications 10054 }
        

tekelecDeviceDiscoveryFailed NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "An error occured in the discovery of network devices"
    ::= { eagleXgDsrMIBNotifications 10055 }
        

oAGTSgMaxAllowedHARoleWarn NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server Group Max Allowed HA Role Warning"
    ::= { eagleXgDsrMIBNotifications 10073 }
        

hASbyRecoveryInProgress NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Standby server temporarily degraded while the new active server stabilizes following switch of activity"
    ::= { eagleXgDsrMIBNotifications 10074 }
        

failureRecoveryWithoutAppRestart NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The Applications on the Standby server have not been restarted after an active to standby transition since h_FailureCleanupMode is set to 0"
    ::= { eagleXgDsrMIBNotifications 10078 }
        

tekelecIncompatibleDatabaseVersionNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The database version is incompatible with the installed software database version"
    ::= { eagleXgDsrMIBNotifications 10000 }
        

hAMtceStopApplications NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The server is no longer providing services because application processes have been manually stopped"
    ::= { eagleXgDsrMIBNotifications 10075 }
        

tekelecLogExportStart NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Log files export operation started"
    ::= { eagleXgDsrMIBNotifications 10100 }
        

tekelecLogExportSuccess NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Log files export operation completed successfully"
    ::= { eagleXgDsrMIBNotifications 10101 }
        

tekelecLogExportFailed NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Log files export operation Failed"
    ::= { eagleXgDsrMIBNotifications 10102 }
        

tekelecLogExportNotRun NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Log files export operation not run - export can only run on Active Network OAMP server"
    ::= { eagleXgDsrMIBNotifications 10103 }
        

tekelecExportXferFailed NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Performance data export remote copy operation Failed"
    ::= { eagleXgDsrMIBNotifications 10104 }
        

tekelecLogExportCancelledUser NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Log files export operation cancelled by user"
    ::= { eagleXgDsrMIBNotifications 10105 }
        

tekelecLogExportCancelledDuplicate NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Log files export operation cancelled - scheduled export already queued"
    ::= { eagleXgDsrMIBNotifications 10106 }
        

tekelecLogExportCancelledQueue NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Log files export operation cancelled - export queue is full"
    ::= { eagleXgDsrMIBNotifications 10107 }
        

tekelecLogExportDupSchedTask NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Duplicate scheduled export task queued"
    ::= { eagleXgDsrMIBNotifications 10108 }
        

tekelecLogExportQueueFull NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Export queue is full"
    ::= { eagleXgDsrMIBNotifications 10109 }
        

certificateAboutToExpire NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Certificate about to expire"
    ::= { eagleXgDsrMIBNotifications 10110 }
        

certificateExpired NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Certificate expired"
    ::= { eagleXgDsrMIBNotifications 10111 }
        

certificateCannotBeUsed NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Certificate cannot be used"
    ::= { eagleXgDsrMIBNotifications 10112 }
        

tekelecLogHealthCheckStart NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Upgrade health check operation started"
    ::= { eagleXgDsrMIBNotifications 10115 }
        

tekelecLogHealthCheckSuccess NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Upgrade health check operation completed successfully"
    ::= { eagleXgDsrMIBNotifications 10116 }
        

tekelecLogHealthCheckFailed NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Upgrade health check operation Failed"
    ::= { eagleXgDsrMIBNotifications 10117 }
        

tekelecLogHealthCheckNotRun NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Upgrade health check operation not run"
    ::= { eagleXgDsrMIBNotifications 10118 }
        

tekelecLogSgUpgradeStart NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server group upgrade operation started"
    ::= { eagleXgDsrMIBNotifications 10120 }
        

tekelecLogSgUpgradeCancelled NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server group upgrade cancelled - validation failed"
    ::= { eagleXgDsrMIBNotifications 10121 }
        

tekelecLogSgUpgradeSuccess NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server group upgrade operation completed successfully"
    ::= { eagleXgDsrMIBNotifications 10122 }
        

tekelecLogSgUpgradeFailed NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server group upgrade operation failed"
    ::= { eagleXgDsrMIBNotifications 10123 }
        

tekelecLogSgUpgradeCancelledUser NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server group upgrade cancelled by user"
    ::= { eagleXgDsrMIBNotifications 10124 }
        

tekelecLogSgUpgradeFailAlm NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server group upgrade operation failed"
    ::= { eagleXgDsrMIBNotifications 10125 }
        

tekelecLogServerUpgradeStart NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server upgrade operation started"
    ::= { eagleXgDsrMIBNotifications 10130 }
        

tekelecLogServerUpgradeCancelled NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server upgrade cancelled - validation failed"
    ::= { eagleXgDsrMIBNotifications 10131 }
        

tekelecLogServerUpgradeSuccess NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server upgrade operation completed successfully"
    ::= { eagleXgDsrMIBNotifications 10132 }
        

tekelecLogServerUpgradeFailed NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server upgrade operation failed"
    ::= { eagleXgDsrMIBNotifications 10133 }
        

tekelecLogServerUpgradeFailAlm NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Server upgrade operation failed"
    ::= { eagleXgDsrMIBNotifications 10134 }
        

tekelecLogSiteUpgradeStart NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Site upgrade operation started"
    ::= { eagleXgDsrMIBNotifications 10140 }
        

tekelecLogSiteUpgradeCancelled NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Site upgrade cancelled - validation failed"
    ::= { eagleXgDsrMIBNotifications 10141 }
        

tekelecLogSiteUpgradeSuccess NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Site upgrade operation completed successfully"
    ::= { eagleXgDsrMIBNotifications 10142 }
        

tekelecLogSiteUpgradeFailed NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Site upgrade operation failed"
    ::= { eagleXgDsrMIBNotifications 10143 }
        

tekelecLogSiteUpgradeCancelledUser NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Site upgrade cancelled by user"
    ::= { eagleXgDsrMIBNotifications 10144 }
        

tekelecLogSiteUpgradeFailAlm NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Site upgrade operation failed"
    ::= { eagleXgDsrMIBNotifications 10145 }
        

tekelecLoginSuccess NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Login Successful"
    ::= { eagleXgDsrMIBNotifications 10151 }
        

tekelecLoginFailed NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Login Failed"
    ::= { eagleXgDsrMIBNotifications 10152 }
        

tekelecLogoutSuccess NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Logout Successful"
    ::= { eagleXgDsrMIBNotifications 10153 }
        

tekelecAccountDisabled NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "User Account disabled due to multiple login failures"
    ::= { eagleXgDsrMIBNotifications 10154 }
        

tekelecSamlLoginSuccess NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SAML Login Successful"
    ::= { eagleXgDsrMIBNotifications 10155 }
        

tekelecSamlLoginFailed NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SAML Login Failed"
    ::= { eagleXgDsrMIBNotifications 10156 }
        

apwSgDbReinit NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Remote Database re-initialization in progress"
    ::= { eagleXgDsrMIBNotifications 10200 }
        

apwBackupFailure NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Database backup failed"
    ::= { eagleXgDsrMIBNotifications 10020 }
        

apwSnmpTrappingNotConfiguredForSite NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SNMP Trapping Not Configured for Site"
    ::= { eagleXgDsrMIBNotifications 10300 }
        



awpss7RemoteSccpSubsystemProhibitedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The status of remote SCCP subsystem has changed to Prohibited."
    ::= { eagleXgDsrMIBNotifications 19240 }
        

awpss7SccpMsgTypeUnrecognizedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SCCP discarded an ingress message because the message was malformed or unsupported. The following connectionless message types are supported: UDT, XUDT, UDTS, and XUDTS. The following SCMG Message Types are supported: SSA, SSP, and SST."
    ::= { eagleXgDsrMIBNotifications 19241 }
        

awpss7SccpHopCounterViolationNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SCCP discarded message because a Hop Counter violation was detected."
    ::= { eagleXgDsrMIBNotifications 19242 }
        

awpss7SccpRoutingFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SCCP was unable to route or process a message during SCCP processing for reasons (other than a global title translation failure, detected SCCP loop) possibly requiring operator intervention."
    ::= { eagleXgDsrMIBNotifications 19243 }
        

awpss7SccpRoutingFailureNetworkStatusNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SCCP was unable to route or process a message during SCCP processing due to transient conditions such as RSP/Destination failures, Remote or Local Subsystem failures."
    ::= { eagleXgDsrMIBNotifications 19244 }
        

awpss7SccpGttFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SCCP Global Title Translation has failed to determine a destination for a PDU -- invoking message return procedure."
    ::= { eagleXgDsrMIBNotifications 19245 }
        

awpss7SccpSegmentationFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SCCP Segmentation Procedure Failure."
    ::= { eagleXgDsrMIBNotifications 19248 }
        

awpss7SccpReassemblyFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SCCP Reassembly Procedure Failure."
    ::= { eagleXgDsrMIBNotifications 19249 }
        

awpss7SCCPLocalSubsystemProhibitedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The status of Local SCCP subsystem has changed to Prohibited"
    ::= { eagleXgDsrMIBNotifications 19246 }
        

awpss7TimedOutWaitingForAspUpAckNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Timed out waiting for ASP-UP-ACK"
    ::= { eagleXgDsrMIBNotifications 19226 }
        

awpss7ReceivedUnsolicitedAspDownAckNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Received unsolicited ASP-DOWN-ACK "
    ::= { eagleXgDsrMIBNotifications 19227 }
        

awpss7TimedOutWaitingForAspActiveAckNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Timed out waiting for ASP-ACTIVE-ACK"
    ::= { eagleXgDsrMIBNotifications 19229 }
        

awpss7ReceivedUnsolicitedAspInactiveAckNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Received unsolicited ASP-INACTIVE-ACK "
    ::= { eagleXgDsrMIBNotifications 19230 }
        

awpss7ReceivedInvalidM3uaMessageNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Received invalid M3UA message"
    ::= { eagleXgDsrMIBNotifications 19231 }
        

awpss7FailedToSendNonDataMessageNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Failed to send non-DATA message"
    ::= { eagleXgDsrMIBNotifications 19233 }
        

awpss7LocalLinkMaintenanceStateChangeNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Local link maintenance state change "
    ::= { eagleXgDsrMIBNotifications 19234 }
        

awpss7ReceivedM3uaErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Received M3UA ERROR "
    ::= { eagleXgDsrMIBNotifications 19235 }
        

awpss7M3rlRspUnavailableNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Unable to access the SS7 Destination Point Code because the RSP status is Unavailable."
    ::= { eagleXgDsrMIBNotifications 19200 }
        

awpss7M3rlRouteUnavailableNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Unable to access the SS7 Destination Point Code via this route."
    ::= { eagleXgDsrMIBNotifications 19201 }
        

awpss7M3rlLinksetUnavailableNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The SS7 linkset to an adjacent SP has failed."
    ::= { eagleXgDsrMIBNotifications 19202 }
        

awpss7M3rlLinkUnavailableNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "M3UA has reported to M3RL that a link is out of service."
    ::= { eagleXgDsrMIBNotifications 19203 }
        

awpss7M3rlPreferredRouteUnavailableNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "M3RL has started to utilize a lower priority (higher cost) route to route traffic toward a given destination address, because the higher priority (lower cost) route specified for that RSP/Destination has become Unavailable."
    ::= { eagleXgDsrMIBNotifications 19204 }
        

awpss7M3rlNodeIsolatedAllLinkDownNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Node isolated - All links down "
    ::= { eagleXgDsrMIBNotifications 19217 }
        

awpss7M3rlTfpReceivedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "TFP message received by M3RL layer."
    ::= { eagleXgDsrMIBNotifications 19205 }
        

awpss7M3rlTfaReceivedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "TFA message received by M3RL layer."
    ::= { eagleXgDsrMIBNotifications 19206 }
        

awpss7M3rlTfrReceivedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "TFR message received by M3RL layer."
    ::= { eagleXgDsrMIBNotifications 19207 }
        

awpss7M3rlTfcReceivedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "TFC message received by M3RL layer."
    ::= { eagleXgDsrMIBNotifications 19208 }
        

awpss7M3rlRoutingFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message was discarded due to a routing error."
    ::= { eagleXgDsrMIBNotifications 19209 }
        

awpss7M3rlRoutingFailureInvalidNiNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message was discarded due to a routing error - the NI value received in a message from the network is not assigned to the MP."
    ::= { eagleXgDsrMIBNotifications 19210 }
        

awpss7M3rlRoutingFailureInvalidSiNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message was discarded due to a routing error - the SI value received in a message from the network is associated with a User Part that is not currently supported. "
    ::= { eagleXgDsrMIBNotifications 19211 }
        

awpss7Ss7ProcessCpuUtilizationNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The SS7 Process, which is responsible for handling all SS7 traffic, is approaching or exceeding its engineered traffic handling capacity."
    ::= { eagleXgDsrMIBNotifications 19250 }
        

awpss7IngressMsgRateNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The ingress message rate (messages per second) for the MP is approaching or exceeding its engineered traffic handling capacity."
    ::= { eagleXgDsrMIBNotifications 19251 }
        

awpss7PduBufferPoolUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the MP's PDU buffer pool is approaching its maximum capacity."
    ::= { eagleXgDsrMIBNotifications 19252 }
        

awpss7SccpStackEventQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the MP's SCCP Stack Event Queue is approaching its maximum capacity."
    ::= { eagleXgDsrMIBNotifications 19253 }
        

awpss7M3rlStackEventQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the MP's M3RL Stack Event Queue is approaching its maximum capacity."
    ::= { eagleXgDsrMIBNotifications 19254 }
        

awpss7M3rlNetMgmtEventQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the MP's M3RL Network Management Event Queue is approaching its maximum capacity."
    ::= { eagleXgDsrMIBNotifications 19255 }
        

awpss7M3uaStackEventQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the MP's M3UA Stack Event Queue is approaching its maximum capacity."
    ::= { eagleXgDsrMIBNotifications 19256 }
        

awpss7SctpAggregateAssocWriteQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of events queued to all SCTP associations on the MP server is approaching maximum capacity."
    ::= { eagleXgDsrMIBNotifications 19258 }
        

awpss7TcapOpDiscardedLocalResLimitNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Operation discarded due to local resource limitation"
    ::= { eagleXgDsrMIBNotifications 19259 }
        

awpss7TcapTransNotDeliveredToPeerNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Transaction could not be delivered to remote TCAP peer due to conditions in the network"
    ::= { eagleXgDsrMIBNotifications 19260 }
        

awpss7TcapMalformedComponentFromRemoteNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Operation discarded due to malformed component received from remote TCAP peer."
    ::= { eagleXgDsrMIBNotifications 19262 }
        

awpss7TcapMalformedDialogueFromLocalNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Transaction discarded due to malformed dialogue message received from local TC User."
    ::= { eagleXgDsrMIBNotifications 19263 }
        

awpss7TcapMalformedDialogueFromRemoteNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Transaction discarded due to malformed dialogue message from remote TCAP peer."
    ::= { eagleXgDsrMIBNotifications 19264 }
        

awpss7TcapUnexpectedMsgFromLocalNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Unexpected event received from local TC User."
    ::= { eagleXgDsrMIBNotifications 19265 }
        

awpss7TcapUnexpectedMsgFromRemoteNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Unexpected event received from remote TCAP peer."
    ::= { eagleXgDsrMIBNotifications 19266 }
        

awpss7TcapDialogueRemovedTimerExpiryNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Dialogue removed by dialogue cleanup timer."
    ::= { eagleXgDsrMIBNotifications 19267 }
        

awpss7TcapOperationRemovedTimerExpiryNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Operation removed by invocation timer expiry."
    ::= { eagleXgDsrMIBNotifications 19268 }
        

awpss7TcapDialogueAbortByRemoteNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Dialogue aborted by remote TCAP peer."
    ::= { eagleXgDsrMIBNotifications 19269 }
        

awpss7TcapUnsupportedTCAPMsgRcvdNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Received unsupported TCAP message."
    ::= { eagleXgDsrMIBNotifications 19270 }
        

awpss7TcapReturnRejectByRemoteNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Operation rejected by remote TCAP peer."
    ::= { eagleXgDsrMIBNotifications 19271 }
        

awpss7TcapActiveDialogueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "TCAP active dialogue utilization"
    ::= { eagleXgDsrMIBNotifications 19272 }
        

awpss7TcapActiveOperationUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "TCAP active operation utilization"
    ::= { eagleXgDsrMIBNotifications 19273 }
        

awpss7TcapStackEventQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "TCAP stack event queue utilization"
    ::= { eagleXgDsrMIBNotifications 19274 }
        

awpss7TcapReturnErrorFromRemoteNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Return Error from remote TCAP peer."
    ::= { eagleXgDsrMIBNotifications 19275 }
        

awpss7TcapRoutingFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "TCAP was unable to route message due to transient condition such as destination failure or destination unavailability"
    ::= { eagleXgDsrMIBNotifications 19281 }
        

awpss7SccpEgressMsgRateNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The Sccp Egress Message Rate (Message per second) for the MP is approaching or exceeding its engineered traffic handling capacity."
    ::= { eagleXgDsrMIBNotifications 19276 }
        




dbcProcessCpuUtilizationNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The Process, which is responsible for handling all traffic, is approaching or exceeding its engineered traffic handling capacity."
    ::= { eagleXgDsrMIBNotifications 19900 }
        

dbcCfgDbValidationErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "A minor database validation error was detected on the MP server during an update. MP internal database is now out of sync with the configuration database. Subsequent database operations on the MP are ALLOWED."
    ::= { eagleXgDsrMIBNotifications 19901 }
        

dbcCfgDbUpdateFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "A critical database validation error was detected on the MP server during an update. MP internal database is now out of sync with the configuration database. Subsequent database operations on the MP are DISABLED."
    ::= { eagleXgDsrMIBNotifications 19902 }
        

dbcCfgDbPostUpdateErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "A minor database validation error was detected on the MP server after a database update. MP internal database is still in sync with the configuration database. Subsequent database operations on the MP are ALLOWED."
    ::= { eagleXgDsrMIBNotifications 19903 }
        

dbcCfgDbPostFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "A critical database validation error was detected on the MP server after a database update. MP internal database is still in sync with the configuration database. Subsequent database operations on the MP are DISABLED."
    ::= { eagleXgDsrMIBNotifications 19904 }
        

dbcMeasurementInitializationFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "A measurement object failed to initialize."
    ::= { eagleXgDsrMIBNotifications 19905 }
        



eagleXgDiameterMpRxAllRateNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DA-MP ingress message rate threshold crossed."
    ::= { eagleXgDsrMIBNotifications 22201 }
        

eagleXgDiameterMpIngressDropNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DA-MP ingress message discarded or rejected."
    ::= { eagleXgDsrMIBNotifications 8010 }
        

eagleXgDiameterMpRxNgnPsOfferedRateNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DA-MP ingress NGN-PS message rate threshold crossed."
    ::= { eagleXgDsrMIBNotifications 8012 }
        

eagleXgDiameterMpNgnPsStateMismatchNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DA-MP NGN-PS administrative and operational state mismatch."
    ::= { eagleXgDsrMIBNotifications 8013 }
        

eagleXgDiameterMpNgnPsDropNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DA-MP NGN-PS message discarded or rejected."
    ::= { eagleXgDsrMIBNotifications 8014 }
        

eagleXgDiameterNgnPsMsgMisroutedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "NGN-PS message routed to peer DSR lacking NGN-PS support."
    ::= { eagleXgDsrMIBNotifications 8015 }
        

eagleXgDiameterMpP16StateMismatchNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MP P16 Support administrative and operational state mismatch."
    ::= { eagleXgDsrMIBNotifications 8016 }
        

eagleXgDiameterMpTaskCpuCongestedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DA-MP Task CPU utilization threshold crossed."
    ::= { eagleXgDsrMIBNotifications 8017 }
        

eagleXgDiameterP16MsgMisroutedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "P16 message routed to peer DSR lacking P16 support."
    ::= { eagleXgDsrMIBNotifications 8018 }
        

eagleXgDiameterMpAnswerPriorityModeMismatchNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DA-MP Answer Priority Mode administrative and operational state mismatch."
    ::= { eagleXgDsrMIBNotifications 8019 }
        

eagleXgDiameterMpRoutingThreadPoolStateMismatchNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Mismatch in Routing Thread Pool operational state and administrative state."
    ::= { eagleXgDsrMIBNotifications 8020 }
        

eagleXgDiameterMpDiamMsgPoolCongestedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DA-MP Diameter message pool utilization threshold crossed."
    ::= { eagleXgDsrMIBNotifications 22202 }
        

eagleXgDiameterMpCpuCongestedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DA-MP CPU utilization threshold crossed."
    ::= { eagleXgDsrMIBNotifications 22200 }
        

eagleXgDiameterMpMemCongestedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DA-MP memory utilization threshold crossed."
    ::= { eagleXgDsrMIBNotifications 22223 }
        

eagleXgDiameterFsmOpStateUnavailableNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Connection is operationally unavailable."
    ::= { eagleXgDsrMIBNotifications 22101 }
        

eagleXgDiameterFsmOpStateDegradedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Connection is operationally degraded."
    ::= { eagleXgDsrMIBNotifications 22102 }
        

eagleXgDiameterIcRateNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Connection ingress message rate threshold crossed."
    ::= { eagleXgDsrMIBNotifications 22328 }
        

eagleXgDiameterEcRateNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Connection egress message rate threshold crossed."
    ::= { eagleXgDsrMIBNotifications 8011 }
        

eagleXgDiameterMpEvFsmExceptionNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DA-MP connection FSM exception."
    ::= { eagleXgDsrMIBNotifications 8000 }
        

eagleXgDiameterMpEvExceptionNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DA-MP exception."
    ::= { eagleXgDsrMIBNotifications 8001 }
        

eagleXgDiameterMpEvRxExceptionNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DA-MP ingress message processing exception."
    ::= { eagleXgDsrMIBNotifications 8002 }
        

eagleXgDiameterMpEvTxExceptionNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DA-MP egress message processing exception."
    ::= { eagleXgDsrMIBNotifications 8003 }
        

eagleXgDiameterEvFsmAdStateNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Connection FSM admin state change."
    ::= { eagleXgDsrMIBNotifications 8004 }
        

eagleXgDiameterEvFsmOpStateNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Connection FSM operational state change."
    ::= { eagleXgDsrMIBNotifications 8005 }
        

eagleXgDiameterEvFsmExceptionNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Connection FSM exception."
    ::= { eagleXgDsrMIBNotifications 8006 }
        

eagleXgDiameterEvExceptionNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Connection exception."
    ::= { eagleXgDsrMIBNotifications 8007 }
        

eagleXgDiameterEvRxExceptionNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Connection ingress message processing exception."
    ::= { eagleXgDsrMIBNotifications 8008 }
        

eagleXgDiameterEvTxExceptionNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Connection egress message processing exception."
    ::= { eagleXgDsrMIBNotifications 8009 }
        

eagleXgDiameterMpRxDiamAllLenNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DA-MP diameter average ingress message length threshold crossed."
    ::= { eagleXgDsrMIBNotifications 22225 }
        

eagleXgDiameterDclTxTaskQueueCongestedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DCL egress task message queue utilization threshold crossed."
    ::= { eagleXgDsrMIBNotifications 22207 }
        

eagleXgDiameterDclTxConnQueueCongestedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DCL egress connection message queue utilization threshold crossed."
    ::= { eagleXgDsrMIBNotifications 22208 }
        

eagleXgDiameterSctpPathUnavailableNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SCTP multi-homed connection has operationally unavailable path."
    ::= { eagleXgDsrMIBNotifications 22103 }
        

eagleXgDiameterSctpPathMismatchNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SCTP multi-homed connection has path mismatch."
    ::= { eagleXgDsrMIBNotifications 22104 }
        

eagleXgDiameterNormMsgMisroutedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Normal message routed onto diagnostic connection."
    ::= { eagleXgDsrMIBNotifications 8100 }
        

eagleXgDiameterDiagMsgMisroutedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Diagnostic message routed onto normal connection."
    ::= { eagleXgDsrMIBNotifications 8101 }
        

eagleXgDiameterConnectionTxCongestionAlarmNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by or before DSR 7.0."
    ::= { eagleXgDsrMIBNotifications 22105 }
        

eagleXgDiameterIngressMessageDiscardedAlarmNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22106 }
        

eagleXgDiameterIngressMessageDiscardedOverLoadControlAlarmNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22215 }
        

eagleXgDiameterDpdRealmDiscoveryFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Peer Discovery Failure"
    ::= { eagleXgDsrMIBNotifications 25800 }
        

eagleXgDiameterDpdRealmExpiryApproachingNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Realm Expiration Approaching"
    ::= { eagleXgDsrMIBNotifications 25802 }
        

eagleXgDiameterDpdConfigErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Peer Discovery Configuration Error Encountered"
    ::= { eagleXgDsrMIBNotifications 25801 }
        

eagleXgDiameterDpdInconsistentPortAssignmentNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Peer Discovery - Inconsistent Remote Host Port Assignment"
    ::= { eagleXgDsrMIBNotifications 25803 }
        

eagleXgDiameterDpdRealmOperStateChangedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Peer Discovery State Change"
    ::= { eagleXgDsrMIBNotifications 25804 }
        

eagleXgDiameterDoicInvalidSharedTtgRefNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Invalid Shared TTG Reference"
    ::= { eagleXgDsrMIBNotifications 25805 }
        

eagleXgDiameterDoicInvalidInternalSoamSgDesignationNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Invalid Internal SOAM Server Group Designation"
    ::= { eagleXgDsrMIBNotifications 25806 }
        

eagleXgDiameterMpEvFsmAnonFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22150 }
        

eagleXgDiameterEvFsmInitFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22170 }
        

eagleXgDiameterConnUnavailSocketCfgFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22300 }
        

eagleXgDiameterConnCongestionLevelChangeNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22220 }
        

eagleXgDiameterConnUnavailConnInitFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22301 }
        

eagleXgDiameterReceivedMalformedMessageNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22302 }
        

eagleXgDiameterConnUnavailPeerClosedConnNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22303 }
        

eagleXgDiameterConnUnavailProvingFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22304 }
        

eagleXgDiameterConnectionAdminStateChangeNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22305 }
        

eagleXgDiameterConnUnavailTimedOutWaitingForCexNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22306 }
        

eagleXgDiameterConnUnavailTimedOutWaitingForDpxNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22307 }
        

eagleXgDiameterReceivedUnexpectedCexNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22308 }
        

eagleXgDiameterReceivedUnexpectedDwxNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22309 }
        

eagleXgDiameterReceivedUnexpectedDpxNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22310 }
        

eagleXgDiameterReceivedInvalidDiameterMessageNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22311 }
        

eagleXgDiameterFailedToSendDiameterMessageNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22312 }
        

eagleXgDiameterConnUnavailTransportFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22313 }
        

eagleXgDiameterConnUnavailCeaRealmHostVldtnFailNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22314 }
        

eagleXgDiameterConnUnavailPeerIpAddrVldtnFailNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by or before DSR 7.0."
    ::= { eagleXgDsrMIBNotifications 22315 }
        

eagleXgDiameterConnUnavailNoCommonAppsNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22316 }
        

eagleXgDiameterConnRejectedConnAlrdyEstdNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by or before DSR 7.0."
    ::= { eagleXgDsrMIBNotifications 22317 }
        

eagleXgDiameterConnRejectedConnNotEnabledNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by or before DSR 7.0."
    ::= { eagleXgDsrMIBNotifications 22318 }
        

eagleXgDiameterConnUnavailWatchdogFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22319 }
        

eagleXgDiameterInvalidPeerInitdConnNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22320 }
        

eagleXgDiameterConnUnavailDnsResolutionFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22321 }
        

eagleXgDiameterConnProvingSuccessNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22322 }
        

eagleXgDiameterConnDegradedWatchdogSuspectNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by or before DSR 7.0."
    ::= { eagleXgDsrMIBNotifications 22323 }
        

eagleXgDiameterConnUnavailCerValidationFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by or before DSR 7.0."
    ::= { eagleXgDsrMIBNotifications 22324 }
        

eagleXgDiameterConnUnavailCerHostIpAvpVldtnFailNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by or before DSR 7.0."
    ::= { eagleXgDsrMIBNotifications 22325 }
        

eagleXgDiameterConnEstablishedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22326 }
        

eagleXgDiameterInitiatorFunctionDisabledNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22327 }
        

eagleXgDiameterSctpConnectionImpairedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22329 }
        

eagleXgDiameterSctpConnectionCfgMismatchNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22330 }
        

eagleXgDiameterSCTPConnectionPartialMatchingNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22331 }
        

eagleXgDiameterConnRejMaxConnExceededNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by or before DSR 7.0."
    ::= { eagleXgDsrMIBNotifications 22332 }
        

eagleXgDiameterConnRejInsufficientIngressMpsNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by or before DSR 7.0."
    ::= { eagleXgDsrMIBNotifications 22333 }
        

eagleXgDiameterUnexpMessagePriorityInRequestNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22334 }
        

eagleXgDiameterMessagePriorityNotSuppPeerNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22335 }
        

eagleXgDiameterConnRejMHSctpConnAttemptNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by or before DSR 7.0."
    ::= { eagleXgDsrMIBNotifications 22336 }
        

eagleXgDiameterDuplicateConnectionReleasedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22343 }
        

eagleXgDiameterProcessorUnavlblOrCngstedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22344 }
        

eagleXgDiameterCplChangedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22345 }
        

eagleXgDiameterMpResIngressMpsOversubscribedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22346 }
        

eagleXgDiameterMpIngressMessageDiscardedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22347 }
        

eagleXgDiameterMpIngressPri0MessageDiscardedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22216 }
        

eagleXgDiameterMpIngressPri1MessageDiscardedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22217 }
        

eagleXgDiameterMpIngressPri2MessageDiscardedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by DSR 7.2."
    ::= { eagleXgDsrMIBNotifications 22218 }
        

eagleXgDiameterMpRadiusMsgPoolCongestedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DA-MP RADIUS message pool utilization threshold crossed."
    ::= { eagleXgDsrMIBNotifications 8200 }
        

eagleXgDiameterRclRxTaskQueueCongestedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "RCL ingress task message queue utilization threshold crossed."
    ::= { eagleXgDsrMIBNotifications 8201 }
        

eagleXgDiameterRclItrPoolCongestedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "RCL ITR pool utilization threshold crossed."
    ::= { eagleXgDsrMIBNotifications 8202 }
        

eagleXgDiameterRclTxTaskQueueCongestedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "RCL egress task message queue utilization threshold crossed."
    ::= { eagleXgDsrMIBNotifications 8203 }
        

eagleXgDiameterRclEtrPoolCongestedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "RCL ETR pool utilization threshold crossed."
    ::= { eagleXgDsrMIBNotifications 8204 }
        

eagleXgDiameterRadiusXactionFailNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "RADIUS connection transaction failure threshold crossed."
    ::= { eagleXgDsrMIBNotifications 8205 }
        

eagleXgDiameterMpRxRadiusAllLenNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "RADIUS average ingress message length threshold crossed."
    ::= { eagleXgDsrMIBNotifications 8206 }
        

eagleXgDiameterMpRadiusKeyErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DA-MP RADIUS key error."
    ::= { eagleXgDsrMIBNotifications 8207 }
        

eagleXgDiameterDebugRoutingInfoAvpEnabledNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Debug Routing Info AVP is Enabled."
    ::= { eagleXgDsrMIBNotifications 22021 }
        

eagleXgDiameterForwardingLoopDetectedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Ingress Request message received was previously processed by the local node as determined from the Route-Record AVP's received in the message."
    ::= { eagleXgDsrMIBNotifications 22022 }
        

eagleXgDiameterPeerUnavailableNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Unable to access the Diameter Peer because all of the diameter connections are Down."
    ::= { eagleXgDsrMIBNotifications 22051 }
        

eagleXgDiameterPeerDegradedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The peer has some available connections, but less than its minimum connection capacity. Continued routing to this peer may cause congestion or other overload conditions."
    ::= { eagleXgDsrMIBNotifications 22052 }
        

eagleXgDiameterRouteListUnavailableNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Route List is Unavailable"
    ::= { eagleXgDsrMIBNotifications 22053 }
        

eagleXgDiameterRouteListDegradedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Route List Operational Status has changed to Degraded because the current weight of the Route List's Active Route Group has dropped below the Route List's configured minimum route group availability weight."
    ::= { eagleXgDsrMIBNotifications 22054 }
        

eagleXgDiameterNonPreferredRouteGroupInUseNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The highest priority Route Group of a Route List is not being utilized to route Request messages because the highest priority Route Group has either become unavailable or whose weight has dropped below the minimum weight configured for the Route List."
    ::= { eagleXgDsrMIBNotifications 22055 }
        

eagleXgDiameterConnAdminStateInconsistencyNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "An operator request to change the Admin State of a diameter connection was not completely processed due to an internal error."
    ::= { eagleXgDsrMIBNotifications 22056 }
        

eagleXgDiameterEtgRateLimitDegradedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The ETG Rate Limit has exceeded the defined threshold."
    ::= { eagleXgDsrMIBNotifications 22057 }
        

eagleXgDiameterEtgPendingTransLimitDegradedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The ETG Pending Transactions Limit has exceeded the defined threshold."
    ::= { eagleXgDsrMIBNotifications 22058 }
        

eagleXgDiameterEtgMonitoringStoppedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "ETG Rate and Pending Transaction Monitoring is stopped on all configured ETGs."
    ::= { eagleXgDsrMIBNotifications 22061 }
        

eagleXgDiameterEtgEtlScopeInconsistencyNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "ETG Control Scope Inconsistency."
    ::= { eagleXgDsrMIBNotifications 22066 }
        

eagleXgDiameterEtgEtlInvalidAssocNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Invalid ETL - ETG Association."
    ::= { eagleXgDsrMIBNotifications 22067 }
        

eagleXgDiameterTtpDegradedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The TTP's Operational Status has been changed to Degraded."
    ::= { eagleXgDsrMIBNotifications 22072 }
        

eagleXgDiameterTtpThrottlingStoppedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "TTP rate throttling has been suspended due to an internal failure."
    ::= { eagleXgDsrMIBNotifications 22073 }
        

eagleXgDiameterTtpMaxLossPercentageExceededNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The Maximum Loss Percentage Threshold assigned to the TTP has been exceeded."
    ::= { eagleXgDsrMIBNotifications 22074 }
        

eagleXgDiameterArtMatchAppUnavailableNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "ART Rule-X is selected but message is not routed because DSR Application is Disabled or not Available."
    ::= { eagleXgDsrMIBNotifications 22075 }
        

eagleXgDiameterTtgMaxLossPercentageExceededNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The Maximum Loss Percentage Threshold assigned to the Route Group within the Route List has been exceeded."
    ::= { eagleXgDsrMIBNotifications 22076 }
        

eagleXgDiameterMpExcessiveRequestRerouteNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Request reroutes due to Answer response and/or Answer timeout has exceeded the configured threshold on the DA-MP server."
    ::= { eagleXgDsrMIBNotifications 22077 }
        

eagleXgDiameterConnStatusInconsistencyExistsNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Diameter Connection status inconsistencies exist among the DA-MPs in the DSR signaling NE."
    ::= { eagleXgDsrMIBNotifications 22950 }
        

eagleXgDiameterAvgHoldTimeLimitExceededNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The average transaction hold time has exceeded its configured limits."
    ::= { eagleXgDsrMIBNotifications 22224 }
        

eagleXgDiameterPtrBufferPoolUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The DA-MP's PTR buffer pool is approaching its maximum capacity."
    ::= { eagleXgDsrMIBNotifications 22203 }
        

eagleXgDiameterRequestMessageQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The DA-MP's request message queue utilization is approaching its maximum capacity."
    ::= { eagleXgDsrMIBNotifications 22204 }
        

eagleXgDiameterAnswerMessageQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The DA-MP's answer message queue utilization is approaching its maximum capacity."
    ::= { eagleXgDsrMIBNotifications 22205 }
        

eagleXgDiameterRerouteQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The DA-MP's reroute queue utilization is approaching its maximum capacity."
    ::= { eagleXgDsrMIBNotifications 22206 }
        

eagleXgDiameterMessageCopyDisabledNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Diameter Message Copy is Disabled."
    ::= { eagleXgDsrMIBNotifications 22209 }
        

eagleXgDiameterMsgCopyQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The DA-MP's Message Copy queue utilization is approaching its maximum capacity."
    ::= { eagleXgDsrMIBNotifications 22214 }
        

eagleXgDiameterRoutingMpsRateNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message processing rate for this DA-MP is approaching or exceeding its engineered traffic handling capacity."
    ::= { eagleXgDsrMIBNotifications 22221 }
        

eagleXgDiameterLongTimeoutPtrBufferPoolUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The DA-MP's Long Timeout PTR buffer pool is approaching its maximum capacity."
    ::= { eagleXgDsrMIBNotifications 22222 }
        

eagleXgDiameterIngressMsgRejectedDecodingFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message received from a peer that was rejected because of a decoding failure. Decoding failures can include missing mandatory parameters."
    ::= { eagleXgDsrMIBNotifications 22001 }
        

eagleXgDiameterPeerRoutingTableRulesSamePriorityNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "A peer routing table search with a received Request message found more than one highest priority peer routing rule match."
    ::= { eagleXgDsrMIBNotifications 22002 }
        

eagleXgDiameterApplicationIdMismatchWithPeerNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "While attempting to route a request message to a peer, a peer's diameter connection was bypassed because the peer did not support the Application ID for that diameter connection."
    ::= { eagleXgDsrMIBNotifications 22003 }
        

eagleXgDiameterMaxPendingTxnsPerConnExceededNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Routing attempted to select an egress Diameter connection to forward a message but the maximum number of allowed pending transactions queued on the Diameter connection has been reached."
    ::= { eagleXgDsrMIBNotifications 22004 }
        

eagleXgDiameterNoPrtRuleNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "A message not addressed to a peer (either Destination-Host AVP was absent or Destination-Host AVP was present but was not a peer's FQDN) could not be routed because no peer routing rules were found."
    ::= { eagleXgDsrMIBNotifications 22005 }
        

eagleXgDiameterSupportedAppIdsInconsistentNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The list of Application IDs supported by a peer during the Diameter Capabilities Exchange procedure on a particular diameter connection is not identical to one of the list of Application IDs received from the peer over a different available diameter connection to that peer."
    ::= { eagleXgDsrMIBNotifications 22007 }
        

eagleXgDiameterOrphanAnswerResponseReceivedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "An Answer response was received for which no pending request transaction existed resulting in the Answer message being discarded."
    ::= { eagleXgDsrMIBNotifications 22008 }
        

eagleXgDiameterApplicationRoutingTableRulesSamePriorityNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "An application routing table search with a received Request message found more than one highest priority application routing rule match."
    ::= { eagleXgDsrMIBNotifications 22009 }
        

eagleXgDiameterOperationalStatusInconsistencyNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by or before DSR 7.0."
    ::= { eagleXgDsrMIBNotifications 22015 }
        

eagleXgDiameterPeerNodeUnavailableThresholdReachedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Peer Node Alarm Aggregation Threshold Reached."
    ::= { eagleXgDsrMIBNotifications 22016 }
        

eagleXgDiameterRouteListUnavailableThresholdReachedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Route List Alarm Aggregation Threshold Reached."
    ::= { eagleXgDsrMIBNotifications 22017 }
        

eagleXgDiameterSpecifiedDasRouteListNotProvisionedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The DAS Route List specified by the trigger point is not provisioned."
    ::= { eagleXgDsrMIBNotifications 22010 }
        

eagleXgDiameterSpecifiedMCCSNotProvisionedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The Message Copy Config Set specified by the trigger point is not provisioned."
    ::= { eagleXgDsrMIBNotifications 22012 }
        

eagleXgDiameterNoDasRouteListSpecifiedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "No valid DAS Route List has been specified in the Message Copy Config Set."
    ::= { eagleXgDsrMIBNotifications 22014 }
        

eagleXgDiameterNumberOfRetransmitsExceededToDasNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The configured number of Message Copy retransmits has been exceeded for the DAS Peer."
    ::= { eagleXgDsrMIBNotifications 22013 }
        

eagleXgDiameterDaMpLeaderGoActiveNotificationNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "A DA-MP has received a notification from HA that the Maintenance Leader resource should transition to the Active role."
    ::= { eagleXgDsrMIBNotifications 22018 }
        

eagleXgDiameterDaMpLeaderGoOOSNotificationNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "A DA-MP has received a notification from HA that the Maintenance Leader resource should transition to the OOS role."
    ::= { eagleXgDsrMIBNotifications 22019 }
        

eagleXgDiameterCopyMessageSizeExceededNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The generated Copy message size exceedeed the max message size on the system."
    ::= { eagleXgDsrMIBNotifications 22020 }
        

eagleXgDiameterEtgRateCongestionNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The Egress Throttle Group Request Message rate Congestion Level has changed. This will change the Request priority that can be routed to peers and connections in the ETG."
    ::= { eagleXgDsrMIBNotifications 22059 }
        

eagleXgDiameterEtgPendingTransCongestionNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The Egress Throttle Group Pending Transaction Limit Congestion Level has changed. This will change the Request priority that can be routed on peers and connections in the ETG."
    ::= { eagleXgDsrMIBNotifications 22060 }
        

eagleXgDiameterTopoHidingActualHostNameNotFoundNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Topology Hiding could not be applied because the Actual Host Name could not be determined."
    ::= { eagleXgDsrMIBNotifications 22062 }
        

eagleXgDiameterDiameterMaxMsgSizeLimitExceededNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The size of the message encoded by DSR has exceeded its max limits."
    ::= { eagleXgDsrMIBNotifications 22063 }
        

eagleXgDiameterRxRedirectHostNotRoutedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DSR received a Redirect Host Notification that it can accept for processing but cannot continue due to some reason."
    ::= { eagleXgDsrMIBNotifications 22064 }
        

eagleXgDiameterRxRedirectRealmNotRoutedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DSR received a Redirect Realm Notification that it can accept for processing but cannot continue due to some reason."
    ::= { eagleXgDsrMIBNotifications 22065 }
        

eagleXgDiameterTtpEvDoicExceptionNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DOIC Protocol Error."
    ::= { eagleXgDsrMIBNotifications 22068 }
        

eagleXgDiameterTtpEvDoicOlrNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "A DOIC OverLoad Request (OLR) was received from a Peer Node and applied to a configured TTP."
    ::= { eagleXgDsrMIBNotifications 22069 }
        

eagleXgDiameterTtpEvDegradedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "TTP Degraded."
    ::= { eagleXgDsrMIBNotifications 22070 }
        

eagleXgDiameterTtgEvLossChgNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "TTG's Loss Percentage was modified."
    ::= { eagleXgDsrMIBNotifications 22071 }
        

eagleXgDiameterNestedArtPrtSearchErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Loop or Maximum Depth Exceeded in ART or PRT Seach."
    ::= { eagleXgDsrMIBNotifications 22078 }
        

eagleXgDiameterInvalidOriginHostAvpForDoicNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Recieved Invalid Origin Host in Answer or TTP state has changed for DOIC processing."
    ::= { eagleXgDsrMIBNotifications 22081 }
        

eagleXgDiameterInvalidDestRouteListNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "RouteList is not provisioned in System Options. "
    ::= { eagleXgDsrMIBNotifications 22082 }
        

eagleXgDiameterPeerNodeAlarmGroupThresholdReachedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Peer Node Alarm Group Threshold Reached."
    ::= { eagleXgDsrMIBNotifications 25613 }
        

eagleXgDiameterConnectionAlarmGroupThresholdReachedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Connection Alarm Group Threshold Reached."
    ::= { eagleXgDsrMIBNotifications 25614 }
        

eagleXgDiameterIPFEConnUnavailableThresholdReachedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "IPFE Connection Alarm Aggregation Threshold Reached."
    ::= { eagleXgDsrMIBNotifications 22349 }
        

eagleXgDiameterConnUnavailableThresholdReachedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Connection Alarm Aggregation Threshold Reached."
    ::= { eagleXgDsrMIBNotifications 22350 }
        

eagleXgDiameterDaMpProfileNotAssignedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "A DA-MP configuration profile has not been assigned to this DA-MP."
    ::= { eagleXgDsrMIBNotifications 22960 }
        

eagleXgDiameterInsufficientAvailMemNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Available Memory for Feature Set is less than the Required Memory."
    ::= { eagleXgDsrMIBNotifications 22961 }
        

eagleXgDiameterNoDaMpLeaderDetectedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "No DA-MP Leader Detected."
    ::= { eagleXgDsrMIBNotifications 25500 }
        

eagleXgDiameterMultipleDaMpLeadersDetectedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Multiple DA-MP Leader Detected."
    ::= { eagleXgDsrMIBNotifications 25510 }
        

eagleXgDiameterDpiTblMonCbOnLogOverrunNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DPI DB Table Monitoring Overrun has occurred. The eagleXgDsr update sync log used by DB Table monitoring to synchronize Diameter Connection Status among all DA-MP RT-DBs has overrun. The DA-MP's Diameter Connection Status sharing table is automatically audited and re-synced to correct any inconsistencies."
    ::= { eagleXgDsrMIBNotifications 22900 }
        

eagleXgDiameterDpiSldbMonAbnormalErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "An unexpected error occurred during DB Table Monitoring."
    ::= { eagleXgDsrMIBNotifications 22901 }
        

eagleXgDiameterTracingSuspendedAlarmNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "IDIH trace has been suspended due to DA-MP (danger of) CPU congestion."
    ::= { eagleXgDsrMIBNotifications 11500 }
        

eagleXgDiameterTracingThrottledAlarmNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Troubleshooting trace has been throttled on some DA-MPs due to IDIH TTR bandwidth usage exceeding provisioned limit."
    ::= { eagleXgDsrMIBNotifications 11501 }
        

eagleXgDiameterInvalidDihIpAddressAlarmNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  deprecated
    DESCRIPTION
            "Deprecated by or before DSR 7.1"
    ::= { eagleXgDsrMIBNotifications 11504 }
        

eagleXgDiameterNetworkTraceConfigurationErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "An error occurred while configuration of network trace. Please delete the trace definition."
    ::= { eagleXgDsrMIBNotifications 11508 }
        

eagleXgDiameterSiteTraceConfigurationErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "An error occurred while configuration of site trace. Please delete the trace definition."
    ::= { eagleXgDsrMIBNotifications 11509 }
        

eagleXgDiameterNetworkTraceActivationErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Network trace is not active on this site. A temporary error occurred while activation of network trace."
    ::= { eagleXgDsrMIBNotifications 11510 }
        

eagleXgDiameterInvalidDihHostNameAlarmNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Unable to connect via Comagent to remote DIH server with hostname"
    ::= { eagleXgDsrMIBNotifications 11511 }
        

eagleXgDiameterIDIHTraceStartedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "A troubleshooting trace instance was started."
    ::= { eagleXgDsrMIBNotifications 11502 }
        

eagleXgDiameterIDIHTraceStoppedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "A troubleshooting trace instance was stopped."
    ::= { eagleXgDsrMIBNotifications 11503 }
        

eagleXgDiameterInvalidIDIHTraceAvpNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "An IDIH-Trace AVP has been received with an invalid format."
    ::= { eagleXgDsrMIBNotifications 11506 }
        

eagleXgDiameterUnableToRunNetworkTraceAtThisSiteNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "A network trace could not be run at this site because the connection or peer referenced by the trace scope value is not configured at this site. The trace will still run at sites that have this entity configured."
    ::= { eagleXgDsrMIBNotifications 11507 }
        

eagleXgDiameterFwDisabledNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DSR Signaling Firewall is administratively Disabled."
    ::= { eagleXgDsrMIBNotifications 25607 }
        

eagleXgDiameterFwDegradedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DSR Signaling Firewall Operational status is degraded."
    ::= { eagleXgDsrMIBNotifications 25608 }
        

eagleXgDiameterFwCfgInconsistentNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The DSR Signaling Firewall rules do not match the active configuration."
    ::= { eagleXgDsrMIBNotifications 25610 }
        

eagleXgDiameterFirewallConfigErrorEncounteredNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Firewall Configuration Error encountered"
    ::= { eagleXgDsrMIBNotifications 25609 }
        

eagleXgDiameterEtgInvalidDRMPAttrbsNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DRMP attributes of ETG not in synch with Remote ETGs associated with same ETL."
    ::= { eagleXgDsrMIBNotifications 25611 }
        

eagleXgDiameterPingAllLivePeerErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DSR ping echo to next hops have failed. See bin/pingAllLivePeer."
    ::= { eagleXgDsrMIBNotifications 25612 }
        



eagleXgDiameterDsrApplicationUnavailableNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DSR Application is unable to process any messages because it is Unavailable."
    ::= { eagleXgDsrMIBNotifications 22500 }
        

eagleXgDiameterDsrApplicationDegradedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Unable to forward Requests to the DSR Application because it is Degraded."
    ::= { eagleXgDsrMIBNotifications 22501 }
        

eagleXgDiameterDsrApplicationRequestQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The DSR Application Request Message Queue Utilization is approaching its maximum capacity."
    ::= { eagleXgDsrMIBNotifications 22502 }
        

eagleXgDiameterDsrApplicationAnswerQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The DSR Application Answer Message Queue Utilization is approaching its maximum capacity."
    ::= { eagleXgDsrMIBNotifications 22503 }
        

eagleXgDiameterDsrApplicationIngressMsgRateNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The ingress message rate for the DSR Application is approaching or exceeding its engineered traffic handling capacity."
    ::= { eagleXgDsrMIBNotifications 22504 }
        

eagleXgDiameterDsrApplicationEnabledNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DSR Application Admin state was changed to 'enabled'."
    ::= { eagleXgDsrMIBNotifications 22520 }
        

eagleXgDiameterDsrApplicationDisabledNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DSR Application Admin state was changed to 'disabled'."
    ::= { eagleXgDsrMIBNotifications 22521 }
        






cAFEventEgressMessageDiscardedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Egress Message Discarded"
    ::= { eagleXgDsrMIBNotifications 19810 }
        

cAFEventIngressMessageDiscardedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Ingress Message Discarded"
    ::= { eagleXgDsrMIBNotifications 19811 }
        

cAFEventHeartbeatMissedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Peer has not responded to heartbeat."
    ::= { eagleXgDsrMIBNotifications 19814 }
        

cAFEventConnectionStateChangeNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Connection state Changed"
    ::= { eagleXgDsrMIBNotifications 19816 }
        

cAFEventComAgtConfigParamChangeNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent DB Responder detected a change in configurable control option parameter"
    ::= { eagleXgDsrMIBNotifications 19817 }
        

cAFEventComAgtSvcRegChangedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Service Registration State Change"
    ::= { eagleXgDsrMIBNotifications 19830 }
        

cAFEventComAgtSvcOpStateChangedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Service Operational State Changed"
    ::= { eagleXgDsrMIBNotifications 19831 }
        

cAFEventComAgtTransFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Reliable Transaction Failed"
    ::= { eagleXgDsrMIBNotifications 19832 }
        

cAFEventRoutingFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Service Egress Message Discarded"
    ::= { eagleXgDsrMIBNotifications 19833 }
        

cAFEventResourceProviderRegisteredNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Resource-Provider Registered"
    ::= { eagleXgDsrMIBNotifications 19842 }
        

cAFEventResourceStateChangeNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Resource-Provider Resource State Changed"
    ::= { eagleXgDsrMIBNotifications 19843 }
        

cAFEventStaleHBPacketNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Resource-Provider Stale Status Received"
    ::= { eagleXgDsrMIBNotifications 19844 }
        

cAFEventResourceProviderDeRegisteredNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Resource-Provider Deregistered"
    ::= { eagleXgDsrMIBNotifications 19845 }
        

cAFEventResourceUserRegisteredNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Resource-USer Registered"
    ::= { eagleXgDsrMIBNotifications 19850 }
        

cAFEventResourceUserDeRegisteredNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Resource-User Deregistered"
    ::= { eagleXgDsrMIBNotifications 19851 }
        

cAFEventResourceRoutingStateNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Resource Routing State Changed"
    ::= { eagleXgDsrMIBNotifications 19852 }
        

cAFEventHaEgressMessageDiscardedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Resource Egress Message Discarded"
    ::= { eagleXgDsrMIBNotifications 19853 }
        

cAFEventHaRPTTAuditResultNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Resource-Provider Tracking Table Audit Results"
    ::= { eagleXgDsrMIBNotifications 19854 }
        

cAFComAgentMaxConnsInConnGrpNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Max connections per connection group limit is reached."
    ::= { eagleXgDsrMIBNotifications 19863 }
        

cAFEventSvcProvRegStateChangedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Service Provider Registration State Changed"
    ::= { eagleXgDsrMIBNotifications 19856 }
        

cAFEventSvcProvOpStateChangedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Service Provider Operational State Changed"
    ::= { eagleXgDsrMIBNotifications 19857 }
        

cAFEventComAgentRejConnUnknownIpNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Connection Rejected"
    ::= { eagleXgDsrMIBNotifications 19858 }
        

cAFConnectionDownNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Connection Down"
    ::= { eagleXgDsrMIBNotifications 19800 }
        

cAFConnLocalBlockedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Connection Locally Blocked"
    ::= { eagleXgDsrMIBNotifications 19801 }
        

cAFConnRemoteBlockedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Connection Remotely Blocked"
    ::= { eagleXgDsrMIBNotifications 19802 }
        

cAFQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the Communication Agent Task stack queue is approaching defined threshold capacity."
    ::= { eagleXgDsrMIBNotifications 19803 }
        

cAFClientConnWaitNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent configured connection waiting for remote client to establish connection"
    ::= { eagleXgDsrMIBNotifications 19804 }
        

cAFRSUnavailNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Routed Service Unavailable"
    ::= { eagleXgDsrMIBNotifications 19820 }
        

cAFRSDegradedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Routed Service Degraded"
    ::= { eagleXgDsrMIBNotifications 19821 }
        

cAFRSCongestedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Routed Service Congested"
    ::= { eagleXgDsrMIBNotifications 19822 }
        

cAFRSUsingLowPriConnGrpNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent routed service is routing traffic using a connection group that has a lower-priority than another connection group."
    ::= { eagleXgDsrMIBNotifications 19823 }
        

cAFTransUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The ComAgent Reliable Transfer Function is approaching or exceeding its engineered reliable transaction handling capacity."
    ::= { eagleXgDsrMIBNotifications 19824 }
        

cAFTransFailRateNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The number of failed transactions during the sampling period has exceeded configured thresholds."
    ::= { eagleXgDsrMIBNotifications 19825 }
        

cAFConnCongestedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Connection Congested"
    ::= { eagleXgDsrMIBNotifications 19826 }
        

cAFConnAlignFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Failed to Align Connection."
    ::= { eagleXgDsrMIBNotifications 19805 }
        

cAFResourceCongestedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Resource Degraded"
    ::= { eagleXgDsrMIBNotifications 19846 }
        

cAFResourceUnavailNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Resource Unavailable"
    ::= { eagleXgDsrMIBNotifications 19847 }
        

cAFResourceErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Resource Error"
    ::= { eagleXgDsrMIBNotifications 19848 }
        

cAFPoolResUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the Communication Agent CommMessage mempool is approaching defined threshold capacity."
    ::= { eagleXgDsrMIBNotifications 19806 }
        

cAFDataEvPoolResUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the Communication Agent DataEvent mempool is approaching defined threshold capacity."
    ::= { eagleXgDsrMIBNotifications 19818 }
        

cAFUserDataFIFOUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the Communication Agent User Data FIFO Queue is approaching defined threshold capacity."
    ::= { eagleXgDsrMIBNotifications 19807 }
        

cAFMxFIFOUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the Communication Agent Mx FIFO Queue is approaching defined threshold capacity."
    ::= { eagleXgDsrMIBNotifications 19808 }
        

cAFMultipleActivesNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Resource Has Multiple Actives"
    ::= { eagleXgDsrMIBNotifications 19855 }
        

cAFTableMonitorFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "ComAgent Configuration Daemon Table Monitoring Failure"
    ::= { eagleXgDsrMIBNotifications 19860 }
        

cAFScriptFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "ComAgent Configuration Daemon Script Failure"
    ::= { eagleXgDsrMIBNotifications 19861 }
        

cAFIngressRateNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The Communication Agent Ingress Stack Event Rate is approaching its defined threshold capacity."
    ::= { eagleXgDsrMIBNotifications 19862 }
        

cAFEventSuccessSetHostServerHWProfileNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "ComAgent Successfully Set Host Server Hardware Profile"
    ::= { eagleXgDsrMIBNotifications 19864 }
        

cAFEventFailToSetHostServerHWProfileNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "ComAgent Failed to Set Host Server Hardware Profile"
    ::= { eagleXgDsrMIBNotifications 19865 }
        

cAFEventPeerGroupStatusChangeNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Peer Group Status Changed"
    ::= { eagleXgDsrMIBNotifications 19866 }
        

cAFEventPSEgressMessageDiscardedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Peer Group Egress Message Discarded"
    ::= { eagleXgDsrMIBNotifications 19867 }
        

cAFEventConnectionRejectNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Communication Agent Connection Rejected. Connection to peer node is not initiated due to network incompatibility"
    ::= { eagleXgDsrMIBNotifications 19868 }
        

cAFSmsQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the SMS Task stack queue is approaching defined threshold capacity."
    ::= { eagleXgDsrMIBNotifications 19827 }
        

cAFBDFQFullNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The BDF work queue depth size has reached full capacity."
    ::= { eagleXgDsrMIBNotifications 19420 }
        

cAFBDFThrotlNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The BDF subsystem is throttling traffic at sender."
    ::= { eagleXgDsrMIBNotifications 19421 }
        

cAFBroadcastDataFrameworkInvalidStackEventNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The BDF subsystem received a StackEvent that was somehow invalid, corrupt, or could not be delivered to the application."
    ::= { eagleXgDsrMIBNotifications 19422 }
        



eagleXgDiameterRbarMsgRejectedDecodingFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message received was rejected because of a decoding failure."
    ::= { eagleXgDsrMIBNotifications 22400 }
        

eagleXgDiameterRbarUnknownApplIdNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message could not be routed because the Diameter Application ID is not supported."
    ::= { eagleXgDsrMIBNotifications 22401 }
        

eagleXgDiameterRbarUnknownCmdCodeNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message could not be routed because the Diameter Command Code in the ingress Request message is not supported and the Routing Exception was configured to send an Answer response."
    ::= { eagleXgDsrMIBNotifications 22402 }
        

eagleXgDiameterRbarNoRoutingEntityAddrAvpNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message could not be routed because no address AVPs were found in the message and the Routing Exception was configured to send an Answer response."
    ::= { eagleXgDsrMIBNotifications 22403 }
        

eagleXgDiameterRbarNoValidRoutingEntityAddrFoundNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message could not be routed because none of the address AVPs contained a valid address and the Routing Exception was configured to send an Answer response."
    ::= { eagleXgDsrMIBNotifications 22404 }
        

eagleXgDiameterRbarAddrMismatchWithProvisionedAddressNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message could not be routed because a valid address was found that did not match an individual address or address range associated with the Application ID, Command Code, and Routing Entity Type and, the Routing Exception was configured to send an Answer response."
    ::= { eagleXgDsrMIBNotifications 22405 }
        

eagleXgDiameterRbarRoutingAttemptFailureInternalResExhNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message could not be routed because the internal Request Message Queue to the DSR Relay Agent was full."
    ::= { eagleXgDsrMIBNotifications 22406 }
        

eagleXgDiameterRbarRoutingFailureInternalDbInconsistencyNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message could not be routed because an internal address resolution run-time database inconsistency was encountered."
    ::= { eagleXgDsrMIBNotifications 22407 }
        

eagleXgDiameterRbarLocalIdentifierLookupSkippedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Address Range Lookup could not be performed for Local Identifier component of Routing Entity Type External Identifier. Address Resolution used the Destination found using Domain Identifier."
    ::= { eagleXgDsrMIBNotifications 22411 }
        



eagleXgDiameterDeirAppUnavailableNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "EIR Application is Unavailable."
    ::= { eagleXgDsrMIBNotifications 71003 }
        

eagleXgDiameterDeirUdrConnectionDownNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "ComAgent connection between DSR EIR and UDR is down. "
    ::= { eagleXgDsrMIBNotifications 71004 }
        

eagleXgDiameterDeirTpsExceededNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The Message rate is exceeding the supported TPS for DSR EIR application."
    ::= { eagleXgDsrMIBNotifications 71005 }
        

eagleXgDiameterDeirLoggingSuspendedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The DSR EIR Logging is suspended."
    ::= { eagleXgDsrMIBNotifications 71006 }
        

eagleXgDiameterDeirRequestQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "EIR request queue utilization threshold exceeded."
    ::= { eagleXgDsrMIBNotifications 71007 }
        

eagleXgDiameterDeirUdrResponseQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "EIR UDR response queue utilization threshold exceeded."
    ::= { eagleXgDsrMIBNotifications 71008 }
        

eagleXgDiameterDeirAppCongestedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "EIR Application is congested."
    ::= { eagleXgDsrMIBNotifications 71009 }
        

eagleXgDiameterDeirComAgentRegistFailNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "COM Agent routing service registration or service notification registration failed, EIR cannot use the COM Agent service for database queries."
    ::= { eagleXgDsrMIBNotifications 71010 }
        

eagleXgDiameterDeirLogTransferFailNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Fetching of EIR logs failed at SO."
    ::= { eagleXgDsrMIBNotifications 71011 }
        

eagleXgDiameterDeirMsgDecodingFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "EIR application failed to decode the request."
    ::= { eagleXgDsrMIBNotifications 71000 }
        

eagleXgDiameterDeirToDrlQueueExhaustMsgDiscardedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "ECA routing attempt failed due to DRL queue exhaustion."
    ::= { eagleXgDsrMIBNotifications 71001 }
        

eagleXgDiameterDeirMsgEncodingFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "EIR application failed to encode the answer."
    ::= { eagleXgDsrMIBNotifications 71002 }
        

eagleXgDiameterCpaMsgDecodeFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The CPA application could not decode a received Diameter message"
    ::= { eagleXgDsrMIBNotifications 22805 }
        

eagleXgDiameterCpaUnknownAppIdNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The CPA application received a diameter message with a Diameter application id != 3."
    ::= { eagleXgDsrMIBNotifications 22806 }
        

eagleXgDiameterCpaUnknownCmdCodeNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The CPA application received a Diameter message other than an Accounting message."
    ::= { eagleXgDsrMIBNotifications 22807 }
        

eagleXgDiameterCpaSessionNotFoundNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The CPA queried the SBR and did not get a match for the Session Binding Record based on the session id."
    ::= { eagleXgDsrMIBNotifications 22808 }
        

eagleXgDiameterCpaUndeliveredSbrQueryNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "ComAgent failed to deliver a query to the SBR"
    ::= { eagleXgDsrMIBNotifications 22809 }
        

eagleXgDiameterCpaRteFailResourceExhNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "An attempt to route a Diameter message through the DRL has failed due to resource exhaustion."
    ::= { eagleXgDsrMIBNotifications 22810 }
        

eagleXgDiameterCpaAppEventQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The CPA Application's Event Queue Utilization is approaching its maximum capacity."
    ::= { eagleXgDsrMIBNotifications 22811 }
        

eagleXgDiameterCpaMissingAvpNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "A received Diameter Accounting message does not contain a required AVP."
    ::= { eagleXgDsrMIBNotifications 22812 }
        

eagleXgDiameterCpaSbrErrorRespNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "CPA application received an error response in reply to an SBR query."
    ::= { eagleXgDsrMIBNotifications 22813 }
        

eagleXgDiameterCpaHASubResourceUnavailableNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "ComAgent has determined that the addressed HA Sub-Resource is out of service."
    ::= { eagleXgDsrMIBNotifications 22814 }
        

eagleXgDiameterCpaUnexpectedSessionNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The CPA found an existing session that was not expected."
    ::= { eagleXgDsrMIBNotifications 22815 }
        

eagleXgDiameterCpaSbrSubresourceIsUnavailableNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "One or more Charging SBR Subresources are unavailable	   "
    ::= { eagleXgDsrMIBNotifications 22816 }
        



pdraPdraProtocolErrorsInDiameterReqNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Diameter Request message(s) received by PCA contain protocol error(s)."
    ::= { eagleXgDsrMIBNotifications 22700 }
        

pdraPdraProtocolErrorsInDiameterAnsNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Diameter Answer message(s) received by PCA contain protocol error(s)."
    ::= { eagleXgDsrMIBNotifications 22701 }
        

pdraPdraHashingResDoesNotMatchResOrSubResNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Database Hash Function Error. Hash function result does not map to a database resource or sub-resource."
    ::= { eagleXgDsrMIBNotifications 22702 }
        

pdraPdraEgressMsgRoutingFailureDueToDrlQueueExhaustedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Diameter Egress message could not be sent because the DRL Message Queue is full."
    ::= { eagleXgDsrMIBNotifications 22703 }
        

pdraPdraStackEventSendingFailureCAUnavailNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Policy and Charging server to SBR server communication failure."
    ::= { eagleXgDsrMIBNotifications 22704 }
        

pdraPdraPsbrErrorIndicationNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Policy and Charging server received response from SBR server indicating SBR errors."
    ::= { eagleXgDsrMIBNotifications 22705 }
        

pdraPdraBindingKeyNotFoundNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Binding Key Not Found In Diameter Message. Binding Key not found in received CCR-I message."
    ::= { eagleXgDsrMIBNotifications 22706 }
        

pdraPdraDiameterMessageProcessingFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "PCA failed to process a Diameter message due to the reason detailed in the additional information field."
    ::= { eagleXgDsrMIBNotifications 22707 }
        

pdraPdraBindingRecordNotFoundNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Binding record is not found for the configured binding keys in the binding dependent session-initiation request message."
    ::= { eagleXgDsrMIBNotifications 22718 }
        

pdraPdraMaxSessionsReachedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Binding capable session initiation request failed because maximum allowed session limit reached"
    ::= { eagleXgDsrMIBNotifications 22719 }
        

pdraPdraSessInitReqWithNoApnNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Policy DRA session initiation request received with no APN"
    ::= { eagleXgDsrMIBNotifications 22735 }
        

pdraPdraPsbrResponseQueueUtilizationNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SBR To PCA Response Queue threshold has been exceeded."
    ::= { eagleXgDsrMIBNotifications 22720 }
        

pdraPdraCongestionStateNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Policy and Charging Server operating in congestion."
    ::= { eagleXgDsrMIBNotifications 22721 }
        

pdraPcrfNotConfiguredNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "PCRF Not Configured. Policy DRA has no PCRFs configured."
    ::= { eagleXgDsrMIBNotifications 22729 }
        

pdraPdraConfigErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Policy and Charging message processing could not be successfully completed due to a configuration error."
    ::= { eagleXgDsrMIBNotifications 22730 }
        

pdraPdraDbInconsistencyExistsNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Policy and Charging database inconsistency due to internal data error or internal database table error."
    ::= { eagleXgDsrMIBNotifications 22731 }
        

pdraPcaFunctionDisabledNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "PCA Function is unable to process any messages because it is Disabled. "
    ::= { eagleXgDsrMIBNotifications 22708 }
        

pdraPcaFunctionUnavailableNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "PCA Function is Unavailable. "
    ::= { eagleXgDsrMIBNotifications 22709 }
        

pdraPcaConfDbNotSyncedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Configuration Database is not synced between the System OAM and Network OAM&P."
    ::= { eagleXgDsrMIBNotifications 22737 }
        

eagleXgDiameterEnhSuspBindingFeatEnabledNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The Enhanced Suspect Binding Feature has been ENABLED."
    ::= { eagleXgDsrMIBNotifications 22750 }
        

eagleXgDiameterEnhSuspectBindingAuditSuppressionNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The binding SBR audit function is suppressed by the Enhanced Suspect Binding Removal feature."
    ::= { eagleXgDsrMIBNotifications 22751 }
        

eagleXgDiameterPcaGeneratedRARRouteErrNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "RAA with Unable To Deliver (3002) error is received at PCA for the locally generated RAR."
    ::= { eagleXgDsrMIBNotifications 22741 }
        

eagleXgDiameterPcaCongestionStateNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "PCA Server Congested Due to Composite Resource Congestion"
    ::= { eagleXgDsrMIBNotifications 22743 }
        



ipfeIpfeBackendUnavailableNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "A backend server has indicated through the monitoring protocol that it is dead."
    ::= { eagleXgDsrMIBNotifications 5001 }
        

ipfeIpfeStateSyncConfigErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "An address pertaining to inter-IPFE state synchronization is configured incorrectly."
    ::= { eagleXgDsrMIBNotifications 5002 }
        

ipfeIpfeStateSyncRunErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Error syncing state data between IPFEs."
    ::= { eagleXgDsrMIBNotifications 5003 }
        

ipfeIpfeIpTablesConfigErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Configuration of IP address information is wrong or incomplete."
    ::= { eagleXgDsrMIBNotifications 5004 }
        

ipfeIpfeBackendInStasisNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "A backend server not accepting new connections but continuing to process existing connections."
    ::= { eagleXgDsrMIBNotifications 5005 }
        

ipfeIpfeEtherDeviceReadErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "A failure occurred reading from an Ethernet device. Restart IPFE process."
    ::= { eagleXgDsrMIBNotifications 5006 }
        

ipfeIpfeBackendUnderloadedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Traffic statistics reveal that an application server is processing lower than average load."
    ::= { eagleXgDsrMIBNotifications 5007 }
        

ipfeIpfeBackendOverloadedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Traffic statistics reveal that an application server is processing higher than average load and will not receive new connections."
    ::= { eagleXgDsrMIBNotifications 5008 }
        

ipfeIpfeNoAvailableAppServersNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Application server monitoring has determined that all servers in the target set are unavailable."
    ::= { eagleXgDsrMIBNotifications 5009 }
        

ipfeIpfeErrorParsingIptablesOutputNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "An unknown error parsing Linux iptables output."
    ::= { eagleXgDsrMIBNotifications 5010 }
        

ipfeIpfeSystemErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Error related to system misbehavior or platform misconfiguration, check traces for more information."
    ::= { eagleXgDsrMIBNotifications 5011 }
        

ipfeIpfeSignalingInterfaceNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Heartbeats to monitor the liveness of a signaling interface have timed out."
    ::= { eagleXgDsrMIBNotifications 5012 }
        

ipfeIpfeThrottlingTrafficNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "IPFE has seen traffic in excess of Global Packet Rate Limit and is dropping packets in order to throttle the traffic."
    ::= { eagleXgDsrMIBNotifications 5013 }
        

ipfeIpfeProcessFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  obsolete
    DESCRIPTION
            "An IPFE process has stopped"
    ::= { eagleXgDsrMIBNotifications 5000 }
        

ipfeIpfeTrafficOverloadNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Total IPFE signaling traffic rate is approaching or exceeding its engineered capacity."
    ::= { eagleXgDsrMIBNotifications 5100 }
        

ipfeIpfeCpuOverloadNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "CPU utilization is approaching maximum levels."
    ::= { eagleXgDsrMIBNotifications 5101 }
        

ipfeIpfeDiskUsageNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Disk space utilization is approaching maximum levels."
    ::= { eagleXgDsrMIBNotifications 5102 }
        

ipfeIpfeMemoryOverloadNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "IPFE memory utilization is approaching maximum levels."
    ::= { eagleXgDsrMIBNotifications 5103 }
        


ipfeSbrCongestionStateNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SBR application is in a congested state"
    ::= { eagleXgDsrMIBNotifications 12003 }
        

ipfeSbrActiveSessBindThresholdNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SBR application exceeded its active bindings threshold"
    ::= { eagleXgDsrMIBNotifications 12007 }
        

ipfeSbrProcTermNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SBR application process was terminated"
    ::= { eagleXgDsrMIBNotifications 12010 }
        



eagleXgDiameterFabrAppDpResponseMessageQueueUtilizationNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The FABR Application's DP Response Message Queue Utilization is approaching its maximum capacity."
    ::= { eagleXgDsrMIBNotifications 22631 }
        

eagleXgDiameterComAgentRegistFailNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "COM Agent routing service registration or service notification registration failed, FABR cannot use the COM Agent service for database queries. "
    ::= { eagleXgDsrMIBNotifications 22632 }
        

eagleXgDiameterFabrMsgRejectedDecodingFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message received was rejected because of a decoding failure"
    ::= { eagleXgDsrMIBNotifications 22600 }
        

eagleXgDiameterFabrUnknownApplIdNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message could not be routed because the Diameter Application ID is not supported."
    ::= { eagleXgDsrMIBNotifications 22601 }
        

eagleXgDiameterFabrUnknownCmdCodeNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message could not be routed because the Diameter Command Code in the ingress Request message is not supported and the Routing Exception was configured to send an Answer response."
    ::= { eagleXgDsrMIBNotifications 22602 }
        

eagleXgDiameterFabrNoRoutingEntityAddrAvpNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message could not be routed because no address AVPs were found in the message and the Routing Exception was configured to send an Answer response."
    ::= { eagleXgDsrMIBNotifications 22603 }
        

eagleXgDiameterFabrNoValidUserIdentityAddrFoundNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "No valid User Identity Address is found in the configured AVPs contained in the ingress message."
    ::= { eagleXgDsrMIBNotifications 22604 }
        

eagleXgDiameterFabrNoAddrFoundAtDpNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message could not be routed because no destination address is found to match the valid User Identity address in the response from DP. The Routing Exception was configured to send an Answer response."
    ::= { eagleXgDsrMIBNotifications 22605 }
        

eagleXgDiameterFabrDpErrorsNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "FABR application received service notification indicating Database (DP) or DB connection (COM Agent) Errors (DP timeout, errors or COM Agent internal errors) for the sent database query.  "
    ::= { eagleXgDsrMIBNotifications 22606 }
        

eagleXgDiameterFabrRoutingAttemptFailureDrlQueueExhNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message could not be routed because the internal Request Message Queue to the DSR Relay Agent was full."
    ::= { eagleXgDsrMIBNotifications 22607 }
        

eagleXgDiameterFabrDpCongestedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "FABR could not send a database query either because the COM Agent reported DP congestion level of (CL=2 or 3), or an abatement period is in progress.  "
    ::= { eagleXgDsrMIBNotifications 22608 }
        

eagleXgDiameterFabrDbConnectionExhNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Database query could not be sent because the database connection (COM Agent) queue was full."
    ::= { eagleXgDsrMIBNotifications 22609 }
        

eagleXgDiameterFabrBlacklistedSubscriberNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message could not be routed because valid User Identity Address extracted from diameter request belongs to blacklisted subscriber."
    ::= { eagleXgDsrMIBNotifications 22611 }
        

eagleXgDiameterFabrDpCongestionStateChangeNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "FABR application received status notification indicating DP congestion state changed or DP congestion abatement time period has completed."
    ::= { eagleXgDsrMIBNotifications 22610 }
        



eagleXgDiameterGlaBindingSubresourceUnavailableNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "GLA is unable to communicate with SBR-Binding.  One or more binding sub-resources are unavailable"
    ::= { eagleXgDsrMIBNotifications 33120 }
        

eagleXgDiameterGlaRespTaskMessageQueueUtilizationNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "GLA's SBR-B Response Message Queue Utilization is approaching its maximum capacity"
    ::= { eagleXgDsrMIBNotifications 33121 }
        

eagleXgDiameterGlaMessageDecodingFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message received was rejected because of a decoding failure"
    ::= { eagleXgDsrMIBNotifications 33100 }
        

eagleXgDiameterGlaIncorrectApplIdOrCmdCodeNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message received was rejected because the Application Id was not GL (16777321) or the Command Code was not GGR (8388655)"
    ::= { eagleXgDsrMIBNotifications 33101 }
        

eagleXgDiameterGlaMissingSubscriberIdNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message received was rejected because it did not contain a User-Name AVP or an MSISDN AVP"
    ::= { eagleXgDsrMIBNotifications 33102 }
        

eagleXgDiameterGlaComAgentErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "GLA was unable to communicate with the SBR-Binding due to a communications error"
    ::= { eagleXgDsrMIBNotifications 33103 }
        

eagleXgDiameterGlaDuplicateSubscriberIdNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message received was rejected because it contained both a User-Name AVP and a MSISDN AVP"
    ::= { eagleXgDsrMIBNotifications 33104 }
        

eagleXgDiameterGlaRoutingAttemptFailureDrlQueueExhNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message could not be routed because the internal Answer Message Queue to the DSR Relay Agent was full"
    ::= { eagleXgDsrMIBNotifications 33105 }
        

eagleXgDiameterGlaComAgentTimeoutNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "GLA was unable to communicate with the SBR-Binding database and the query timed out"
    ::= { eagleXgDsrMIBNotifications 33106 }
        



eagleXgDiameterDmiwfAppComagentProviderRegistrationFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DM-IWF application was unable to register for MAP-to-Diameter transaction service.No MAP-to-Diameter transactions can be routed to this DA-MP."
    ::= { eagleXgDsrMIBNotifications 33000 }
        

eagleXgDiameterDmiwfAppComagentUserRegistrationFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DM-IWF application was unable to register for Diameter-to-MAP transaction service. Diameter-to-MAP transactions cannot be service by this DA-MP. "
    ::= { eagleXgDsrMIBNotifications 33001 }
        

eagleXgDiameterDmiwfAppServerPlaceFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DM-IWF DA-MP Server is not associated with an AppWorks Place."
    ::= { eagleXgDsrMIBNotifications 33002 }
        

eagleXgDiameterDmiwfAppInsufficientMemoryFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DA-MP does not have sufficient memory to support DM-IWF."
    ::= { eagleXgDsrMIBNotifications 33003 }
        

eagleXgDiameterDmiwfAppTransactionResponseQueueUtilizationNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The DM-IWF Transaction Response Queue Utilization is approaching its maximum engineered capacity."
    ::= { eagleXgDsrMIBNotifications 33004 }
        

eagleXgDiameterDmiwfAppPTRPoolUtilizationNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The DM-IWF PTR Pool Utilization is approaching its maximum engineered capacity. DM-IWF allocates a pending transaction record (PTR) for every pending Diameter-to-MAP and MAP-to-Diameter transaction.  If this problem persists and the pool reaches 100% utilization, all new ingress messages will be discarded. This alarm should not normally occur when no other congestion alarms are asserted."
    ::= { eagleXgDsrMIBNotifications 33005 }
        

eagleXgDiameterDmiwfAppIncompatibleProfileFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DA-MP has been assigned a profile that is incompatible with DM-IWF"
    ::= { eagleXgDsrMIBNotifications 33014 }
        

eagleXgDiameterMdIwfServiceCongestedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DM-IWF could not forward a Request to MD-IWF due to MD-IWF Service Congestion."
    ::= { eagleXgDsrMIBNotifications 33006 }
        

eagleXgDiameterMdIwfErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DM-IWF received notification indicating ComAgent Error/Timeout or MD-IWF Application generated Failure Response."
    ::= { eagleXgDsrMIBNotifications 33007 }
        

eagleXgDiameterDmiwfMaxPendTransactionsAllowedExceededNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DM-IWF rejected either a Diameter-to-MAP or MAP-to-Diameter transaction because it was unable to allocation a pending transaction record (PTR) for the transaction. DM-IWF allocates a PTR for every pending Diameter-to-MAP and MAP-to-Diameter transaction.  If this problem persists and the pool reaches 100% utilization, all new ingress messages will be discarded. This alarm should not normally occur when no other congestion alarms are asserted."
    ::= { eagleXgDsrMIBNotifications 33008 }
        

eagleXgDiameterDmiwfUnexpectedAnswerRspReceivedFromSS7MPNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "No pending transaction was found for the Answer response received from SS7-MP. When a Request message is forwarded to an SS7-MP, DM-IWF creates a pending transaction record (PTR). The PTR is abandoned if an Answer response is not received in a timely fashion. "
    ::= { eagleXgDsrMIBNotifications 33009 }
        

eagleXgDiameterDmiwfMapComAgentConnectionExhaustedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DM-IWF failed to enqueue Request or Answer to ComAgent."
    ::= { eagleXgDsrMIBNotifications 33010 }
        

eagleXgDiameterDmiwfAnswerTimeoutNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DM-IWF failed to receive a Diameter Answer in response to a Diameter Request that was forwarded to MD-IWF Routed Service, within the DM-IWF Pending Answer Timer expiration."
    ::= { eagleXgDsrMIBNotifications 33011 }
        

eagleXgDiameterDmiwfDecodeErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The decoder has reported an error causing the Request to be discarded."
    ::= { eagleXgDsrMIBNotifications 33012 }
        

eagleXgDiameterDrlQueueExhaustionNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DM-IWF failed to forward a Diameter message to DRL due to DRL queue exhaustion"
    ::= { eagleXgDsrMIBNotifications 33013 }
        

eagleXgDiameterDmiwfMaxDiameterMsgSizeExceededNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DM-IWF failed to forward the Diameter message to SS7-MP because the message size exceeds supported maximum message size."
    ::= { eagleXgDsrMIBNotifications 33015 }
        


eagleXgDiameterCapmGenericInfoAlarmNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Capm Generic Event"
    ::= { eagleXgDsrMIBNotifications 25005 }
        

eagleXgDiameterCapmGenericMinorAlarmNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Capm Generic Alarm - Minor"
    ::= { eagleXgDsrMIBNotifications 25006 }
        

eagleXgDiameterCapmGenericMajorAlarmNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Capm Generic Alarm - Major"
    ::= { eagleXgDsrMIBNotifications 25007 }
        

eagleXgDiameterCapmGenericCriticalAlarmNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Capm Generic Alarm - Critical"
    ::= { eagleXgDsrMIBNotifications 25008 }
        

eagleXgDiameterCapmUpdateFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Rule Template failed to be updated"
    ::= { eagleXgDsrMIBNotifications 25000 }
        

eagleXgDiameterCapmActionFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Action failed within the Rule Template"
    ::= { eagleXgDsrMIBNotifications 25001 }
        

eagleXgDiameterCapmExitRuleFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Stop Rule Template processing after action failure"
    ::= { eagleXgDsrMIBNotifications 25002 }
        

eagleXgDiameterCapmExitTriggerFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Exit Trigger point after action failure"
    ::= { eagleXgDsrMIBNotifications 25003 }
        

eagleXgDiameterCapmScriptLoadingFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Script syntax error"
    ::= { eagleXgDsrMIBNotifications 25004 }
        



eagleXgDiameterPSBRDbOpFailNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "An error occurred during a SBR database operation."
    ::= { eagleXgDsrMIBNotifications 22711 }
        

eagleXgDiameterPSBRStkEvFailComAgentNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SBR received an error or timeout response from Communication Agent when sending a stack event to another SBR server."
    ::= { eagleXgDsrMIBNotifications 22712 }
        

eagleXgDiameterPSBRAltKeyCreateFailNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Failed to create an Alternate Key record in the Binding database."
    ::= { eagleXgDsrMIBNotifications 22713 }
        

eagleXgDiameterPSBRRARInitiationErrNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SBR encountered an error while processing PCA initiated RAR requests."
    ::= { eagleXgDsrMIBNotifications 22714 }
        

eagleXgDiameterPSBRAuditStatisticsReportNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SBR Audit Statistics Report"
    ::= { eagleXgDsrMIBNotifications 22716 }
        

eagleXgDiameterUSBRAuditStatisticsReportNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "U-SBR Database Audit Statistics Report"
    ::= { eagleXgDsrMIBNotifications 33730 }
        

eagleXgDiameterPSbrActSessThreshNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Number of SBR sessions threshold for a Policy and Charging Mated Sites Place Association has been exceeded."
    ::= { eagleXgDsrMIBNotifications 22710 }
        

eagleXgDiameterPSbrMemUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SBR server memory utilization threshold has been exceeded."
    ::= { eagleXgDsrMIBNotifications 22724 }
        

eagleXgDiameterPSbrServerInCongestionNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SBR server operating in congestion."
    ::= { eagleXgDsrMIBNotifications 22725 }
        

eagleXgDiameterPSbrStackEvQUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SBR server stack event queue utilization threshold has been exceeded."
    ::= { eagleXgDsrMIBNotifications 22726 }
        

eagleXgDiameterPSbrInitializationFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SBR server process failed to initialize."
    ::= { eagleXgDsrMIBNotifications 22727 }
        

eagleXgDiameterPSbrActBindThreshNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Number of bindings threshold has been exceeded."
    ::= { eagleXgDsrMIBNotifications 22728 }
        

eagleXgDiameterPSbrProcCpuThreshNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SBR process CPU utilization threshold has been exceeded."
    ::= { eagleXgDsrMIBNotifications 22732 }
        

eagleXgDiameterPSBRAuditSuspendedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SBR audit is suspended due to congestion."
    ::= { eagleXgDsrMIBNotifications 22715 }
        

eagleXgDiameterPSBRAltKeyCreationFailureRateNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SBR Alternate Key Creation Failure rate exceeds threshold."
    ::= { eagleXgDsrMIBNotifications 22717 }
        

eagleXgDiameterPSBRPostMigrationMemFreeNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SBR failed to free binding memory after PCRF Pooling binding migration"
    ::= { eagleXgDsrMIBNotifications 22733 }
        

eagleXgDiameterPSBRPostPcaFunctionDisableMemFreeNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SBR failed to free shared memory after after admin state of a PCA function is changed to disable"
    ::= { eagleXgDsrMIBNotifications 22736 }
        

eagleXgDiameterPSBRProcessNotRunningNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "A managed SBR process cannot be started or has unexpectedly terminated"
    ::= { eagleXgDsrMIBNotifications 22752 }
        

pdraPdraUnexpectedSEDownVersionNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Policy and Charging server received a stack event with an unexpected down-version"
    ::= { eagleXgDsrMIBNotifications 22734 }
        

pdraPdraBindingSubresourceUnavailableNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "One or more Policy Binding sub-resources are unavailable."
    ::= { eagleXgDsrMIBNotifications 22722 }
        

pdraPdraSessionSubresourceUnavailableNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "One or more Policy and Charging Session sub-resources are unavailable."
    ::= { eagleXgDsrMIBNotifications 22723 }
        

eagleXgDiameterSbrReconfigStateTransitionNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SBR Database Reconfiguration State Transition"
    ::= { eagleXgDsrMIBNotifications 22738 }
        

eagleXgDiameterPSbrReconfigConditionsErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Failed to successfully complete an SBR Reconfiguration Plan"
    ::= { eagleXgDsrMIBNotifications 22740 }
        

eagleXgDiameterEnhancedOverloadCtrlAdminStateMismatchNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Enhanced Overload Control administrative and operational state mismatch."
    ::= { eagleXgDsrMIBNotifications 22742 }
        



awptransmgrTransportDownNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Transport Down"
    ::= { eagleXgDsrMIBNotifications 19400 }
        

awptransmgrTransSingleWriteQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the MP's single Transport Egress-Queue is approaching its maximum capacity."
    ::= { eagleXgDsrMIBNotifications 19408 }
        

awptransmgrFailedToConfigureTransportNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Failed to configure transport"
    ::= { eagleXgDsrMIBNotifications 19401 }
        

awptransmgrFailedToConnectTransportNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Failed to connect Transport"
    ::= { eagleXgDsrMIBNotifications 19402 }
        

awptransmgrReceivedMalformedTransSctpMessageNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Received malformed SCTP message (invalid length)"
    ::= { eagleXgDsrMIBNotifications 19403 }
        

awptransmgrFarEndClosedTheTransportNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Far-end closed the transport"
    ::= { eagleXgDsrMIBNotifications 19404 }
        

awptransmgrTransportClosedDueToLackOfResponseNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Transport closed due to lack of response"
    ::= { eagleXgDsrMIBNotifications 19405 }
        

awptransmgrLocalTransportMaintenanceStateChangeNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Local Transport maintenance state change "
    ::= { eagleXgDsrMIBNotifications 19406 }
        

awptransmgrFailedToSendTransDataMessageNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Failed to send Transport DATA message"
    ::= { eagleXgDsrMIBNotifications 19407 }
        

awptransmgrMessageRejectedByAclFilteringNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The message is rejected based on configured Access Control List for Transport"
    ::= { eagleXgDsrMIBNotifications 19409 }
        

awptransmgrAdjIpAddrStateChangeNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "State change of an IP Address of a multihomed Adjacent Node in SCTP Transport."
    ::= { eagleXgDsrMIBNotifications 19410 }
        

awptransmgrSctpTransportRefusedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SCTP Transport closed due to failure of multihoming validation"
    ::= { eagleXgDsrMIBNotifications 19411 }
        

awptransmgrSctpTransportCfgMismatchNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "IP addresses advertised by an Adjacent Node in INIT/INIT-ACK chunk are different from configured IP Addresses."
    ::= { eagleXgDsrMIBNotifications 19412 }
        

awptransmgrTransportClosedDueToUnsupportedEventNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SCTP Transport closed due to unsupported add/delete peer IP Address event received in Peer Address Notification"
    ::= { eagleXgDsrMIBNotifications 19413 }
        



eagleXgDiameterMdIwfIngressMsgRateNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Ingress message rate for the MD-IWF Application is approaching or exceeding its engineered traffic handling capacity."
    ::= { eagleXgDsrMIBNotifications 33050 }
        

eagleXgDiameterMdIwfApplDegradedOrUnavailableNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MD-IWF Application operational status is Degraded or Unavailable."
    ::= { eagleXgDsrMIBNotifications 33051 }
        

eagleXgDiameterMdIwfUserSvcDownNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MD-IWF is notified via ComAgent that the rolled-up DM-IWF Service Status is Down."
    ::= { eagleXgDsrMIBNotifications 33052 }
        

eagleXgDiameterMdIwfDiamTransQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MD-IWF Application DiamTrans Task Queue Utilization is approaching its maximum capacity."
    ::= { eagleXgDsrMIBNotifications 33053 }
        

eagleXgDiameterMdIwfMapTransQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MD-IWF Application MapTrans Task Queue Utilization is approaching its maximum capacity."
    ::= { eagleXgDsrMIBNotifications 33054 }
        

eagleXgDiameterMdIwfDampInterfaceQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MD-IWF Application DAMPInterface Task Queue Utilization is approaching its maximum capacity."
    ::= { eagleXgDsrMIBNotifications 33055 }
        

eagleXgDiameterMdIwfComAgentProviderRegisFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MD-IWF Application was unable to register with ComAgent as a provider of the MDIWFSvc service. No Diameter-to-MAP transactions can be routed to this SS7-MP."
    ::= { eagleXgDsrMIBNotifications 33056 }
        

eagleXgDiameterMdIwfComAgentUserRegisFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MD-IWF Application was unable to register with ComAgent as a user of the DMIWFSvc service. MAP-to-Diameter transactions cannot be processed by this SS7-MP."
    ::= { eagleXgDsrMIBNotifications 33057 }
        

eagleXgDiameterMdIwfDiamToMapPtrUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MD-IWF Application DiamToMap PTR Utilization is approaching its maximum engineered capacity."
    ::= { eagleXgDsrMIBNotifications 33058 }
        

eagleXgDiameterMdIwfMapToDiamPtrUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MD-IWF Application MapToDiam PTR Utilization is approaching its maximum engineered capacity."
    ::= { eagleXgDsrMIBNotifications 33059 }
        

eagleXgDiameterSs7MpProfileNotAssignedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "A SS7-MP configuration profile has not been assigned to this SS7-MP."
    ::= { eagleXgDsrMIBNotifications 33060 }
        

eagleXgDiameterMdIwfInsufficientMemoryForMdiwfNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SS7-MP does not have sufficient memory to support MD-IWF"
    ::= { eagleXgDsrMIBNotifications 33062 }
        

eagleXgDiameterMdIwfSs7MpNotAssocWithPlaceNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MD-IWF SS7-MP Server is not associated with an AppWorks Place."
    ::= { eagleXgDsrMIBNotifications 33063 }
        

eagleXgDiameterMdIwfResourceExhaustionNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MD-IWF Application is unable to process a message due to resource exhaustion."
    ::= { eagleXgDsrMIBNotifications 33065 }
        

eagleXgDiameterMdIwfOrphanDiamAnswerNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MD-IWF Application received a Diameter Answer message for which no Pending Transaction Record exists."
    ::= { eagleXgDsrMIBNotifications 33066 }
        

eagleXgDiameterMdIwfOrphanMapResponseNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MD-IWF Application received a MAP response message for which no Pending Transaction Record exists."
    ::= { eagleXgDsrMIBNotifications 33067 }
        

eagleXgDiameterMdIwfMapResponseTimeoutNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MD-IWF Application sent a MAP request message to the SS7 network, but timed out waiting for the MAP response."
    ::= { eagleXgDsrMIBNotifications 33068 }
        

eagleXgDiameterMdIwfDiamAnswerTimeoutNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MD-IWF Application sent a Diameter Request message to the DA-MP, but timed out waiting for the Diameter Answer."
    ::= { eagleXgDsrMIBNotifications 33069 }
        

eagleXgDiameterMdIwfGeneratedDiamErrorAnswerNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "An exception occurred while MD-IWF was processing a Diameter Request message, causing it to generate a Diameter Answer error message."
    ::= { eagleXgDsrMIBNotifications 33070 }
        

eagleXgDiameterMdIwfGeneratedMapErrorResponseNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "An exception occurred while MD-IWF was processing a MAP Request message, causing it to generate a MAP response error message."
    ::= { eagleXgDsrMIBNotifications 33071 }
        

eagleXgDiameterMdIwfTcapNoticeRecdNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MD-IWF Application received a TCAP Notice from the SS7 network."
    ::= { eagleXgDsrMIBNotifications 33072 }
        

eagleXgDiameterMdIwfAdminStateEnabledNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MD-IWF Application admin state was changed to Enabled on the SS7-MP."
    ::= { eagleXgDsrMIBNotifications 33073 }
        

eagleXgDiameterMdIwfAdminStateDisabledNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MD-IWF Application admin state was changed to Disabled on the SS7-MP."
    ::= { eagleXgDsrMIBNotifications 33074 }
        

eagleXgDiameterMdIwfRcvdComAgtErrorOrDmiwfNckNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MD-IWF sent a Diameter Request message to DM-IWF that resulted in a ComAgent error / timeout or in a DM-IWF NACK."
    ::= { eagleXgDsrMIBNotifications 33075 }
        

eagleXgDiameterMdIwfDiamAnsRcvdFrmUnexcpDaMpNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MD-IWF received a Diameter Answer from a different DA-MP than the one that sent the immediate response."
    ::= { eagleXgDsrMIBNotifications 33076 }
        

eagleXgDiameterMdIwfAddressTranslationFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MD-IWF was not able to perform address translation due to a lookup error in a configuration table, or else due to a missing or unexpected parameter / AVP."
    ::= { eagleXgDsrMIBNotifications 33077 }
        

eagleXgDiameterMdIwfDiamEirRecdDestHostNotPresentNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MD-IWF Application received a Diameter EIR message but the Destination-Host AVP was either (1) not present or (2) the Destination-Host AVP value was not present in table DiamIdentityGta."
    ::= { eagleXgDsrMIBNotifications 33078 }
        

eagleXgDiameterMdIwfMessageTranslationFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MD-IWF attempt to perform message translation was unsuccessful."
    ::= { eagleXgDsrMIBNotifications 33079 }
        

eagleXgDiameterMdIwfEdlEncodeFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "EDL failure occurred while MD-IWF attempted to encode a Diameter message."
    ::= { eagleXgDsrMIBNotifications 33080 }
        



eagleXgDiameterLoadGenAppSenderMessageQueueUtilizationNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The LoadGen Sender Message Queue Utilization is approaching its maximum capacity."
    ::= { eagleXgDsrMIBNotifications 33025 }
        

eagleXgDiameterLoadGenAppReceiverMessageQueueUtilizationNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The LoadGen Receiver Message Queue Utilization is approaching its maximum capacity."
    ::= { eagleXgDsrMIBNotifications 33026 }
        

eagleXgDiameterLoadGenAppTransactionEventPoolUtilizationNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The LoadGen Transaction Event Pool utilization is approaching its maximum capacity."
    ::= { eagleXgDsrMIBNotifications 33027 }
        

eagleXgDiameterLoadGenAppPtrPoolUtilizationNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The LoadGen Pending Transaction Record Pool utilization is approaching its maximum capacity."
    ::= { eagleXgDsrMIBNotifications 33028 }
        




dcaDSRAppUdrEventMessageQueueUtilizationNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The DSR Application UDR Event Queue Utilization is approaching its maximum capacity.   "
    ::= { eagleXgDsrMIBNotifications 33303 }
        

dcaDSRAppRuntimeErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The script generates runtime errors.  "
    ::= { eagleXgDsrMIBNotifications 33304 }
        

dcaDSRAppProcedureNotFoundNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The Perl interpreter attempts to invoke an inexistent procedure.   "
    ::= { eagleXgDsrMIBNotifications 33305 }
        

dcaDSRAppUsbrResFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The U-SBR DB logical name could not be resolved to a physical U-SBR DB.   "
    ::= { eagleXgDsrMIBNotifications 33306 }
        

dcaDSRAppCompileErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The script generates compilation errors."
    ::= { eagleXgDsrMIBNotifications 33309 }
        

dcaDSRSubresourceUnavaiableNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "One or more U-SBR server groups hosting a U-SBR DB are unavailable.   "
    ::= { eagleXgDsrMIBNotifications 33310 }
        

dcaDSRAppScriptGenerationErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The script could not be saved in the /tmp/appworks_temp directory.   "
    ::= { eagleXgDsrMIBNotifications 33312 }
        

dcaDSRUsbrLogicalNameErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "No mapping has been provisioned for the U-SBR logical name.   "
    ::= { eagleXgDsrMIBNotifications 33313 }
        

dcaCustomMealDiffErrorNotification NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The differentiation, un-differentiation or update process of a Custom MEAL has been interrupted and will be retried in 10 seconds"
    ::= { eagleXgDsrMIBNotifications 33314 }
        

dcaCustomNotification101Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33330 }
        

dcaCustomNotification102Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33331 }
        

dcaCustomNotification103Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33332 }
        

dcaCustomNotification104Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33333 }
        

dcaCustomNotification105Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33334 }
        

dcaCustomNotification106Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33335 }
        

dcaCustomNotification107Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33336 }
        

dcaCustomNotification108Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33337 }
        

dcaCustomNotification109Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33338 }
        

dcaCustomNotification110Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33339 }
        

dcaCustomNotification111Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33340 }
        

dcaCustomNotification112Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33341 }
        

dcaCustomNotification113Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33342 }
        

dcaCustomNotification114Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33343 }
        

dcaCustomNotification115Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33344 }
        

dcaCustomNotification116Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33345 }
        

dcaCustomNotification117Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33346 }
        

dcaCustomNotification118Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33347 }
        

dcaCustomNotification119Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33348 }
        

dcaCustomNotification120Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33349 }
        

dcaCustomNotification121Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33350 }
        

dcaCustomNotification122Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33351 }
        

dcaCustomNotification123Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33352 }
        

dcaCustomNotification124Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33353 }
        

dcaCustomNotification125Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33354 }
        

dcaCustomNotification601Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33831 }
        

dcaCustomNotification602Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33832 }
        

dcaCustomNotification603Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33833 }
        

dcaCustomNotification604Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33834 }
        

dcaCustomNotification605Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33835 }
        

dcaCustomNotification606Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33836 }
        

dcaCustomNotification607Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33837 }
        

dcaCustomNotification608Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33838 }
        

dcaCustomNotification609Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33839 }
        

dcaCustomNotification610Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33840 }
        

dcaCustomNotification611Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33841 }
        

dcaCustomNotification612Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33842 }
        

dcaCustomNotification613Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33843 }
        

dcaCustomNotification614Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33844 }
        

dcaCustomNotification615Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33845 }
        

dcaCustomNotification616Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33846 }
        

dcaCustomNotification617Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33847 }
        

dcaCustomNotification618Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33848 }
        

dcaCustomNotification619Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33849 }
        

dcaCustomNotification620Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33850 }
        

dcaCustomNotification621Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33851 }
        

dcaCustomNotification622Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33852 }
        

dcaCustomNotification623Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33853 }
        

dcaCustomNotification624Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33854 }
        

dcaCustomNotification625Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33855 }
        

dcaCustomNotification626Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33856 }
        

dcaCustomNotification627Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33857 }
        

dcaCustomNotification628Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33858 }
        

dcaCustomNotification629Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33859 }
        

dcaCustomNotification630Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33860 }
        

dcaCustomNotification631Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33861 }
        

dcaCustomNotification632Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33862 }
        

dcaCustomNotification633Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33863 }
        

dcaCustomNotification634Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33864 }
        

dcaCustomNotification635Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33865 }
        

dcaCustomNotification636Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33866 }
        

dcaCustomNotification637Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33867 }
        

dcaCustomNotification638Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33868 }
        

dcaCustomNotification639Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33869 }
        

dcaCustomNotification640Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33870 }
        

dcaCustomNotification641Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33871 }
        

dcaCustomNotification642Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33872 }
        

dcaCustomNotification643Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33873 }
        

dcaCustomNotification644Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33874 }
        

dcaCustomNotification645Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33875 }
        

dcaCustomNotification646Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33876 }
        

dcaCustomNotification647Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33877 }
        

dcaCustomNotification648Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33878 }
        

dcaCustomNotification649Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33879 }
        

dcaCustomNotification650Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33880 }
        

dcaCustomNotification651Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33881 }
        

dcaCustomNotification652Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33882 }
        

dcaCustomNotification653Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33883 }
        

dcaCustomNotification654Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33884 }
        

dcaCustomNotification655Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33885 }
        

dcaCustomNotification656Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33886 }
        

dcaCustomNotification657Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33887 }
        

dcaCustomNotification658Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33888 }
        

dcaCustomNotification659Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33889 }
        

dcaCustomNotification660Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33890 }
        

dcaCustomNotification661Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33891 }
        

dcaCustomNotification662Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33892 }
        

dcaCustomNotification663Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33893 }
        

dcaCustomNotification664Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33894 }
        

dcaCustomNotification665Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33895 }
        

dcaCustomNotification666Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33896 }
        

dcaCustomNotification667Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33897 }
        

dcaCustomNotification668Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33898 }
        

dcaCustomNotification669Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33899 }
        

dcaCustomNotification670Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33900 }
        

dcaCustomNotification671Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33901 }
        

dcaCustomNotification672Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33902 }
        

dcaCustomNotification673Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33903 }
        

dcaCustomNotification674Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33904 }
        

dcaCustomNotification675Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33905 }
        

dcaCustomNotification676Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33906 }
        

dcaCustomNotification677Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33907 }
        

dcaCustomNotification678Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33908 }
        

dcaCustomNotification679Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33909 }
        

dcaCustomNotification680Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33910 }
        

dcaCustomNotification681Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33911 }
        

dcaCustomNotification682Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33912 }
        

dcaCustomNotification683Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33913 }
        

dcaCustomNotification684Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33914 }
        

dcaCustomNotification685Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33915 }
        

dcaCustomNotification686Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33916 }
        

dcaCustomNotification687Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33917 }
        

dcaCustomNotification688Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33918 }
        

dcaCustomNotification689Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33919 }
        

dcaCustomNotification690Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33920 }
        

dcaCustomNotification691Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33921 }
        

dcaCustomNotification692Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33922 }
        

dcaCustomNotification693Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33923 }
        

dcaCustomNotification694Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33924 }
        

dcaCustomNotification695Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33925 }
        

dcaCustomNotification696Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33926 }
        

dcaCustomNotification697Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33927 }
        

dcaCustomNotification698Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33928 }
        

dcaCustomNotification699Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33929 }
        

dcaCustomNotification700Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33930 }
        

dcaCustomNotification51Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33355 }
        

dcaCustomNotification52Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33356 }
        

dcaCustomNotification53Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33357 }
        

dcaCustomNotification54Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33358 }
        

dcaCustomNotification55Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33359 }
        

dcaCustomNotification56Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33360 }
        

dcaCustomNotification57Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33361 }
        

dcaCustomNotification58Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33362 }
        

dcaCustomNotification59Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33363 }
        

dcaCustomNotification60Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33364 }
        

dcaCustomNotification61Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33365 }
        

dcaCustomNotification62Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33366 }
        

dcaCustomNotification63Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33367 }
        

dcaCustomNotification64Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33368 }
        

dcaCustomNotification65Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33369 }
        

dcaCustomNotification66Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33370 }
        

dcaCustomNotification67Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33371 }
        

dcaCustomNotification68Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33372 }
        

dcaCustomNotification69Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33373 }
        

dcaCustomNotification70Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33374 }
        

dcaCustomNotification71Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33375 }
        

dcaCustomNotification72Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33376 }
        

dcaCustomNotification73Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33377 }
        

dcaCustomNotification74Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33378 }
        

dcaCustomNotification75Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33379 }
        

dcaCustomNotification401Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33931 }
        

dcaCustomNotification402Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33932 }
        

dcaCustomNotification403Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33933 }
        

dcaCustomNotification404Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33934 }
        

dcaCustomNotification405Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33935 }
        

dcaCustomNotification406Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33936 }
        

dcaCustomNotification407Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33937 }
        

dcaCustomNotification408Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33938 }
        

dcaCustomNotification409Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33939 }
        

dcaCustomNotification410Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33940 }
        

dcaCustomNotification411Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33941 }
        

dcaCustomNotification412Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33942 }
        

dcaCustomNotification413Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33943 }
        

dcaCustomNotification414Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33944 }
        

dcaCustomNotification415Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33945 }
        

dcaCustomNotification416Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33946 }
        

dcaCustomNotification417Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33947 }
        

dcaCustomNotification418Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33948 }
        

dcaCustomNotification419Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33949 }
        

dcaCustomNotification420Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33950 }
        

dcaCustomNotification421Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33951 }
        

dcaCustomNotification422Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33952 }
        

dcaCustomNotification423Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33953 }
        

dcaCustomNotification424Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33954 }
        

dcaCustomNotification425Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33955 }
        

dcaCustomNotification426Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33956 }
        

dcaCustomNotification427Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33957 }
        

dcaCustomNotification428Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33958 }
        

dcaCustomNotification429Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33959 }
        

dcaCustomNotification430Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33960 }
        

dcaCustomNotification431Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33961 }
        

dcaCustomNotification432Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33962 }
        

dcaCustomNotification433Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33963 }
        

dcaCustomNotification434Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33964 }
        

dcaCustomNotification435Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33965 }
        

dcaCustomNotification436Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33966 }
        

dcaCustomNotification437Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33967 }
        

dcaCustomNotification438Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33968 }
        

dcaCustomNotification439Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33969 }
        

dcaCustomNotification440Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33970 }
        

dcaCustomNotification441Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33971 }
        

dcaCustomNotification442Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33972 }
        

dcaCustomNotification443Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33973 }
        

dcaCustomNotification444Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33974 }
        

dcaCustomNotification445Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33975 }
        

dcaCustomNotification446Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33976 }
        

dcaCustomNotification447Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33977 }
        

dcaCustomNotification448Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33978 }
        

dcaCustomNotification449Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33979 }
        

dcaCustomNotification450Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33980 }
        

dcaCustomNotification451Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33981 }
        

dcaCustomNotification452Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33982 }
        

dcaCustomNotification453Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33983 }
        

dcaCustomNotification454Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33984 }
        

dcaCustomNotification455Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33985 }
        

dcaCustomNotification456Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33986 }
        

dcaCustomNotification457Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33987 }
        

dcaCustomNotification458Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33988 }
        

dcaCustomNotification459Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33989 }
        

dcaCustomNotification460Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33990 }
        

dcaCustomNotification461Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33991 }
        

dcaCustomNotification462Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33992 }
        

dcaCustomNotification463Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33993 }
        

dcaCustomNotification464Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33994 }
        

dcaCustomNotification465Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33995 }
        

dcaCustomNotification466Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33996 }
        

dcaCustomNotification467Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33997 }
        

dcaCustomNotification468Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33998 }
        

dcaCustomNotification469Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33999 }
        

dcaCustomNotification470Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34000 }
        

dcaCustomNotification471Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34001 }
        

dcaCustomNotification472Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34002 }
        

dcaCustomNotification473Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34003 }
        

dcaCustomNotification474Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34004 }
        

dcaCustomNotification475Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34005 }
        

dcaCustomNotification476Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34006 }
        

dcaCustomNotification477Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34007 }
        

dcaCustomNotification478Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34008 }
        

dcaCustomNotification479Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34009 }
        

dcaCustomNotification480Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34010 }
        

dcaCustomNotification481Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34011 }
        

dcaCustomNotification482Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34012 }
        

dcaCustomNotification483Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34013 }
        

dcaCustomNotification484Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34014 }
        

dcaCustomNotification485Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34015 }
        

dcaCustomNotification486Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34016 }
        

dcaCustomNotification487Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34017 }
        

dcaCustomNotification488Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34018 }
        

dcaCustomNotification489Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34019 }
        

dcaCustomNotification490Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34020 }
        

dcaCustomNotification491Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34021 }
        

dcaCustomNotification492Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34022 }
        

dcaCustomNotification493Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34023 }
        

dcaCustomNotification494Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34024 }
        

dcaCustomNotification495Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34025 }
        

dcaCustomNotification496Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34026 }
        

dcaCustomNotification497Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34027 }
        

dcaCustomNotification498Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34028 }
        

dcaCustomNotification499Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34029 }
        

dcaCustomNotification500Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34030 }
        

dcaCustomNotification126Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33380 }
        

dcaCustomNotification127Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33381 }
        

dcaCustomNotification128Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33382 }
        

dcaCustomNotification129Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33383 }
        

dcaCustomNotification130Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33384 }
        

dcaCustomNotification131Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33385 }
        

dcaCustomNotification132Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33386 }
        

dcaCustomNotification133Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33387 }
        

dcaCustomNotification134Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33388 }
        

dcaCustomNotification135Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33389 }
        

dcaCustomNotification136Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33390 }
        

dcaCustomNotification137Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33391 }
        

dcaCustomNotification138Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33392 }
        

dcaCustomNotification139Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33393 }
        

dcaCustomNotification140Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33394 }
        

dcaCustomNotification141Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33395 }
        

dcaCustomNotification142Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33396 }
        

dcaCustomNotification143Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33397 }
        

dcaCustomNotification144Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33398 }
        

dcaCustomNotification145Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33399 }
        

dcaCustomNotification146Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33400 }
        

dcaCustomNotification147Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33401 }
        

dcaCustomNotification148Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33402 }
        

dcaCustomNotification149Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33403 }
        

dcaCustomNotification150Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33404 }
        

dcaCustomNotification701Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34031 }
        

dcaCustomNotification702Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34032 }
        

dcaCustomNotification703Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34033 }
        

dcaCustomNotification704Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34034 }
        

dcaCustomNotification705Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34035 }
        

dcaCustomNotification706Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34036 }
        

dcaCustomNotification707Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34037 }
        

dcaCustomNotification708Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34038 }
        

dcaCustomNotification709Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34039 }
        

dcaCustomNotification710Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34040 }
        

dcaCustomNotification711Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34041 }
        

dcaCustomNotification712Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34042 }
        

dcaCustomNotification713Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34043 }
        

dcaCustomNotification714Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34044 }
        

dcaCustomNotification715Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34045 }
        

dcaCustomNotification716Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34046 }
        

dcaCustomNotification717Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34047 }
        

dcaCustomNotification718Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34048 }
        

dcaCustomNotification719Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34049 }
        

dcaCustomNotification720Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34050 }
        

dcaCustomNotification721Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34051 }
        

dcaCustomNotification722Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34052 }
        

dcaCustomNotification723Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34053 }
        

dcaCustomNotification724Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34054 }
        

dcaCustomNotification725Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34055 }
        

dcaCustomNotification726Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34056 }
        

dcaCustomNotification727Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34057 }
        

dcaCustomNotification728Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34058 }
        

dcaCustomNotification729Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34059 }
        

dcaCustomNotification730Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34060 }
        

dcaCustomNotification731Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34061 }
        

dcaCustomNotification732Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34062 }
        

dcaCustomNotification733Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34063 }
        

dcaCustomNotification734Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34064 }
        

dcaCustomNotification735Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34065 }
        

dcaCustomNotification736Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34066 }
        

dcaCustomNotification737Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34067 }
        

dcaCustomNotification738Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34068 }
        

dcaCustomNotification739Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34069 }
        

dcaCustomNotification740Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34070 }
        

dcaCustomNotification741Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34071 }
        

dcaCustomNotification742Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34072 }
        

dcaCustomNotification743Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34073 }
        

dcaCustomNotification744Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34074 }
        

dcaCustomNotification745Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34075 }
        

dcaCustomNotification746Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34076 }
        

dcaCustomNotification747Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34077 }
        

dcaCustomNotification748Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34078 }
        

dcaCustomNotification749Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34079 }
        

dcaCustomNotification750Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34080 }
        

dcaCustomNotification751Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34081 }
        

dcaCustomNotification752Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34082 }
        

dcaCustomNotification753Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34083 }
        

dcaCustomNotification754Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34084 }
        

dcaCustomNotification755Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34085 }
        

dcaCustomNotification756Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34086 }
        

dcaCustomNotification757Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34087 }
        

dcaCustomNotification758Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34088 }
        

dcaCustomNotification759Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34089 }
        

dcaCustomNotification760Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34090 }
        

dcaCustomNotification761Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34091 }
        

dcaCustomNotification762Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34092 }
        

dcaCustomNotification763Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34093 }
        

dcaCustomNotification764Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34094 }
        

dcaCustomNotification765Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34095 }
        

dcaCustomNotification766Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34096 }
        

dcaCustomNotification767Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34097 }
        

dcaCustomNotification768Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34098 }
        

dcaCustomNotification769Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34099 }
        

dcaCustomNotification770Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34100 }
        

dcaCustomNotification771Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34101 }
        

dcaCustomNotification772Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34102 }
        

dcaCustomNotification773Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34103 }
        

dcaCustomNotification774Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34104 }
        

dcaCustomNotification775Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34105 }
        

dcaCustomNotification776Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34106 }
        

dcaCustomNotification777Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34107 }
        

dcaCustomNotification778Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34108 }
        

dcaCustomNotification779Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34109 }
        

dcaCustomNotification780Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34110 }
        

dcaCustomNotification781Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34111 }
        

dcaCustomNotification782Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34112 }
        

dcaCustomNotification783Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34113 }
        

dcaCustomNotification784Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34114 }
        

dcaCustomNotification785Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34115 }
        

dcaCustomNotification786Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34116 }
        

dcaCustomNotification787Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34117 }
        

dcaCustomNotification788Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34118 }
        

dcaCustomNotification789Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34119 }
        

dcaCustomNotification790Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34120 }
        

dcaCustomNotification791Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34121 }
        

dcaCustomNotification792Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34122 }
        

dcaCustomNotification793Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34123 }
        

dcaCustomNotification794Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34124 }
        

dcaCustomNotification795Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34125 }
        

dcaCustomNotification796Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34126 }
        

dcaCustomNotification797Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34127 }
        

dcaCustomNotification798Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34128 }
        

dcaCustomNotification799Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34129 }
        

dcaCustomNotification800Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34130 }
        

dcaCustomNotification76Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33405 }
        

dcaCustomNotification77Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33406 }
        

dcaCustomNotification78Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33407 }
        

dcaCustomNotification79Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33408 }
        

dcaCustomNotification80Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33409 }
        

dcaCustomNotification81Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33410 }
        

dcaCustomNotification82Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33411 }
        

dcaCustomNotification83Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33412 }
        

dcaCustomNotification84Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33413 }
        

dcaCustomNotification85Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33414 }
        

dcaCustomNotification86Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33415 }
        

dcaCustomNotification87Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33416 }
        

dcaCustomNotification88Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33417 }
        

dcaCustomNotification89Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33418 }
        

dcaCustomNotification90Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33419 }
        

dcaCustomNotification91Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33420 }
        

dcaCustomNotification92Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33421 }
        

dcaCustomNotification93Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33422 }
        

dcaCustomNotification94Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33423 }
        

dcaCustomNotification95Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33424 }
        

dcaCustomNotification96Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33425 }
        

dcaCustomNotification97Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33426 }
        

dcaCustomNotification98Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33427 }
        

dcaCustomNotification99Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33428 }
        

dcaCustomNotification100Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33429 }
        

dcaCustomNotification501Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34131 }
        

dcaCustomNotification502Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34132 }
        

dcaCustomNotification503Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34133 }
        

dcaCustomNotification504Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34134 }
        

dcaCustomNotification505Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34135 }
        

dcaCustomNotification506Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34136 }
        

dcaCustomNotification507Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34137 }
        

dcaCustomNotification508Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34138 }
        

dcaCustomNotification509Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34139 }
        

dcaCustomNotification510Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34140 }
        

dcaCustomNotification511Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34141 }
        

dcaCustomNotification512Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34142 }
        

dcaCustomNotification513Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34143 }
        

dcaCustomNotification514Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34144 }
        

dcaCustomNotification515Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34145 }
        

dcaCustomNotification516Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34146 }
        

dcaCustomNotification517Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34147 }
        

dcaCustomNotification518Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34148 }
        

dcaCustomNotification519Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34149 }
        

dcaCustomNotification520Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34150 }
        

dcaCustomNotification521Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34151 }
        

dcaCustomNotification522Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34152 }
        

dcaCustomNotification523Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34153 }
        

dcaCustomNotification524Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34154 }
        

dcaCustomNotification525Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34155 }
        

dcaCustomNotification526Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34156 }
        

dcaCustomNotification527Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34157 }
        

dcaCustomNotification528Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34158 }
        

dcaCustomNotification529Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34159 }
        

dcaCustomNotification530Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34160 }
        

dcaCustomNotification531Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34161 }
        

dcaCustomNotification532Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34162 }
        

dcaCustomNotification533Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34163 }
        

dcaCustomNotification534Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34164 }
        

dcaCustomNotification535Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34165 }
        

dcaCustomNotification536Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34166 }
        

dcaCustomNotification537Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34167 }
        

dcaCustomNotification538Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34168 }
        

dcaCustomNotification539Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34169 }
        

dcaCustomNotification540Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34170 }
        

dcaCustomNotification541Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34171 }
        

dcaCustomNotification542Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34172 }
        

dcaCustomNotification543Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34173 }
        

dcaCustomNotification544Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34174 }
        

dcaCustomNotification545Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34175 }
        

dcaCustomNotification546Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34176 }
        

dcaCustomNotification547Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34177 }
        

dcaCustomNotification548Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34178 }
        

dcaCustomNotification549Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34179 }
        

dcaCustomNotification550Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34180 }
        

dcaCustomNotification551Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34181 }
        

dcaCustomNotification552Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34182 }
        

dcaCustomNotification553Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34183 }
        

dcaCustomNotification554Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34184 }
        

dcaCustomNotification555Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34185 }
        

dcaCustomNotification556Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34186 }
        

dcaCustomNotification557Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34187 }
        

dcaCustomNotification558Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34188 }
        

dcaCustomNotification559Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34189 }
        

dcaCustomNotification560Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34190 }
        

dcaCustomNotification561Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34191 }
        

dcaCustomNotification562Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34192 }
        

dcaCustomNotification563Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34193 }
        

dcaCustomNotification564Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34194 }
        

dcaCustomNotification565Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34195 }
        

dcaCustomNotification566Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34196 }
        

dcaCustomNotification567Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34197 }
        

dcaCustomNotification568Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34198 }
        

dcaCustomNotification569Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34199 }
        

dcaCustomNotification570Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34200 }
        

dcaCustomNotification571Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34201 }
        

dcaCustomNotification572Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34202 }
        

dcaCustomNotification573Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34203 }
        

dcaCustomNotification574Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34204 }
        

dcaCustomNotification575Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34205 }
        

dcaCustomNotification576Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34206 }
        

dcaCustomNotification577Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34207 }
        

dcaCustomNotification578Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34208 }
        

dcaCustomNotification579Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34209 }
        

dcaCustomNotification580Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34210 }
        

dcaCustomNotification581Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34211 }
        

dcaCustomNotification582Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34212 }
        

dcaCustomNotification583Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34213 }
        

dcaCustomNotification584Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34214 }
        

dcaCustomNotification585Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34215 }
        

dcaCustomNotification586Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34216 }
        

dcaCustomNotification587Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34217 }
        

dcaCustomNotification588Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34218 }
        

dcaCustomNotification589Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34219 }
        

dcaCustomNotification590Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34220 }
        

dcaCustomNotification591Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34221 }
        

dcaCustomNotification592Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34222 }
        

dcaCustomNotification593Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34223 }
        

dcaCustomNotification594Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34224 }
        

dcaCustomNotification595Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34225 }
        

dcaCustomNotification596Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34226 }
        

dcaCustomNotification597Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34227 }
        

dcaCustomNotification598Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34228 }
        

dcaCustomNotification599Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34229 }
        

dcaCustomNotification600Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34230 }
        

dcaCustomNotification151Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33430 }
        

dcaCustomNotification152Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33431 }
        

dcaCustomNotification153Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33432 }
        

dcaCustomNotification154Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33433 }
        

dcaCustomNotification155Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33434 }
        

dcaCustomNotification156Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33435 }
        

dcaCustomNotification157Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33436 }
        

dcaCustomNotification158Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33437 }
        

dcaCustomNotification159Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33438 }
        

dcaCustomNotification160Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33439 }
        

dcaCustomNotification161Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33440 }
        

dcaCustomNotification162Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33441 }
        

dcaCustomNotification163Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33442 }
        

dcaCustomNotification164Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33443 }
        

dcaCustomNotification165Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33444 }
        

dcaCustomNotification166Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33445 }
        

dcaCustomNotification167Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33446 }
        

dcaCustomNotification168Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33447 }
        

dcaCustomNotification169Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33448 }
        

dcaCustomNotification170Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33449 }
        

dcaCustomNotification171Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33450 }
        

dcaCustomNotification172Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33451 }
        

dcaCustomNotification173Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33452 }
        

dcaCustomNotification174Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33453 }
        

dcaCustomNotification175Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33454 }
        

dcaCustomNotification176Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33455 }
        

dcaCustomNotification177Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33456 }
        

dcaCustomNotification178Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33457 }
        

dcaCustomNotification179Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33458 }
        

dcaCustomNotification180Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33459 }
        

dcaCustomNotification181Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33460 }
        

dcaCustomNotification182Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33461 }
        

dcaCustomNotification183Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33462 }
        

dcaCustomNotification184Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33463 }
        

dcaCustomNotification185Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33464 }
        

dcaCustomNotification186Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33465 }
        

dcaCustomNotification187Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33466 }
        

dcaCustomNotification188Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33467 }
        

dcaCustomNotification189Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33468 }
        

dcaCustomNotification190Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33469 }
        

dcaCustomNotification191Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33470 }
        

dcaCustomNotification192Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33471 }
        

dcaCustomNotification193Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33472 }
        

dcaCustomNotification194Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33473 }
        

dcaCustomNotification195Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33474 }
        

dcaCustomNotification196Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33475 }
        

dcaCustomNotification197Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33476 }
        

dcaCustomNotification198Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33477 }
        

dcaCustomNotification199Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33478 }
        

dcaCustomNotification200Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 33479 }
        

dcaCustomNotification801Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34231 }
        

dcaCustomNotification802Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34232 }
        

dcaCustomNotification803Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34233 }
        

dcaCustomNotification804Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34234 }
        

dcaCustomNotification805Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34235 }
        

dcaCustomNotification806Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34236 }
        

dcaCustomNotification807Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34237 }
        

dcaCustomNotification808Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34238 }
        

dcaCustomNotification809Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34239 }
        

dcaCustomNotification810Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34240 }
        

dcaCustomNotification811Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34241 }
        

dcaCustomNotification812Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34242 }
        

dcaCustomNotification813Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34243 }
        

dcaCustomNotification814Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34244 }
        

dcaCustomNotification815Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34245 }
        

dcaCustomNotification816Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34246 }
        

dcaCustomNotification817Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34247 }
        

dcaCustomNotification818Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34248 }
        

dcaCustomNotification819Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34249 }
        

dcaCustomNotification820Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34250 }
        

dcaCustomNotification821Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34251 }
        

dcaCustomNotification822Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34252 }
        

dcaCustomNotification823Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34253 }
        

dcaCustomNotification824Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34254 }
        

dcaCustomNotification825Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34255 }
        

dcaCustomNotification826Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34256 }
        

dcaCustomNotification827Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34257 }
        

dcaCustomNotification828Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34258 }
        

dcaCustomNotification829Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34259 }
        

dcaCustomNotification830Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34260 }
        

dcaCustomNotification831Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34261 }
        

dcaCustomNotification832Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34262 }
        

dcaCustomNotification833Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34263 }
        

dcaCustomNotification834Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34264 }
        

dcaCustomNotification835Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34265 }
        

dcaCustomNotification836Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34266 }
        

dcaCustomNotification837Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34267 }
        

dcaCustomNotification838Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34268 }
        

dcaCustomNotification839Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34269 }
        

dcaCustomNotification840Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34270 }
        

dcaCustomNotification841Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34271 }
        

dcaCustomNotification842Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34272 }
        

dcaCustomNotification843Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34273 }
        

dcaCustomNotification844Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34274 }
        

dcaCustomNotification845Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34275 }
        

dcaCustomNotification846Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34276 }
        

dcaCustomNotification847Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34277 }
        

dcaCustomNotification848Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34278 }
        

dcaCustomNotification849Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34279 }
        

dcaCustomNotification850Notify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Undifferentiated"
    ::= { eagleXgDsrMIBNotifications 34280 }
        

dcaEgressMsgRouteFailureDueToDrlQueueExhaustedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Diameter Message Routing Failure Due To Full DRL Queue. Diameter egress message could not be sent because the DRL queue is full."
    ::= { eagleXgDsrMIBNotifications 33307 }
        

dcaComAgentSendFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DCA failed to send query to UDR due to ComAgent Error."
    ::= { eagleXgDsrMIBNotifications 33308 }
        

dcaDcaAppReloadedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The DCA application script has been successfully re-compiled and re-loaded."
    ::= { eagleXgDsrMIBNotifications 33311 }
        

dcaDcaCreateAppVersionFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Dsroam failed to create application version on DcaLifecycleSoam table."
    ::= { eagleXgDsrMIBNotifications 33300 }
        

dcaDcaUpdateConfigDataFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Dsroam failed to synchronize configuration data on SO. "
    ::= { eagleXgDsrMIBNotifications 33301 }
        

dcaDcaDeleteAppVersionFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Dsroam failed to delete application version from DcaLifecycleSoam table."
    ::= { eagleXgDsrMIBNotifications 33302 }
        

dcaDcaLoggingFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DCA Asynchronous Task has suspended/stopped processing of Logging Events."
    ::= { eagleXgDsrMIBNotifications 33315 }
        

dcaDSRAppDcaAsyncMessageQueueUtilizationNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The DSR Application DCA AsyncTask Queue Utilization is approaching its maximum capacity."
    ::= { eagleXgDsrMIBNotifications 33316 }
        

dcaDcaFetchLogErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DCA Fetch Log Script has stopped working on Active SO."
    ::= { eagleXgDsrMIBNotifications 33317 }
        

dcaDCACreateAndSendRequestMessageSendFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Failed While Sending a CreateAndSend Request Message."
    ::= { eagleXgDsrMIBNotifications 33318 }
        



vSTPVstpassociationDownNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Association Down"
    ::= { eagleXgDsrMIBNotifications 70000 }
        

vSTPLinkDownNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Link Down"
    ::= { eagleXgDsrMIBNotifications 70001 }
        

vSTPSctpConnectionRefusedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SCTP Connection refused"
    ::= { eagleXgDsrMIBNotifications 70050 }
        

vSTPFailedtoconfigureConnectionNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Failed to configure Connection"
    ::= { eagleXgDsrMIBNotifications 70051 }
        

vSTPFarendclosedtheconnectionNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Far-end closed the connection"
    ::= { eagleXgDsrMIBNotifications 70052 }
        

vSTPSctpconnectionclosedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SCTP connection closed"
    ::= { eagleXgDsrMIBNotifications 70053 }
        

vSTPRemoteIPAddresstatechangeNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Remote IP Address state change"
    ::= { eagleXgDsrMIBNotifications 70054 }
        

vSTPAssociationadminstatechangeNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Association admin state change "
    ::= { eagleXgDsrMIBNotifications 70055 }
        

vSTPLinkadminStateChangeNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Link admin state change"
    ::= { eagleXgDsrMIBNotifications 70056 }
        

vSTPVstpReceivedInvalidM3UAMessageNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Received Invalid M3UA Message"
    ::= { eagleXgDsrMIBNotifications 70057 }
        

vSTPVstpReceivedM3uaErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Received M3UA ERROR"
    ::= { eagleXgDsrMIBNotifications 70058 }
        

vSTPFailedToSendDataMessageNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Failed to send DATA message"
    ::= { eagleXgDsrMIBNotifications 70059 }
        

vSTPFailedToReceiveDataMessageNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Failed to receive DATA message"
    ::= { eagleXgDsrMIBNotifications 70067 }
        

vSTPM3uaIngressMsgDiscardedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "M3ua Ingress Message Discarded."
    ::= { eagleXgDsrMIBNotifications 70079 }
        

vSTPRemoteBlockedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Remote Blocked."
    ::= { eagleXgDsrMIBNotifications 70389 }
        

vSTPMtp3RspRestrictedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Limited access to the SS7 Destination Point Code because the RSP status is Restricted."
    ::= { eagleXgDsrMIBNotifications 70390 }
        

vSTPMtp3RspUnavailableNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Unable to access the SS7 Destination Point Code because the RSP status is Unavailable."
    ::= { eagleXgDsrMIBNotifications 70002 }
        

vSTPMtp3RouteRestrictedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Limited access to the SS7 Destination Point Code via this route because its Restricted."
    ::= { eagleXgDsrMIBNotifications 70391 }
        

vSTPMtp3RouteUnavailableNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Unable to access the SS7 Destination Point Code via this route."
    ::= { eagleXgDsrMIBNotifications 70003 }
        

vSTPMtp3LinksetUnavailableNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The SS7 linkset to an adjacent SP has failed."
    ::= { eagleXgDsrMIBNotifications 70004 }
        

vSTPMtp3LinkUnavailableNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "M3UA or M2PA has reported to mtp3 that a link is out of service."
    ::= { eagleXgDsrMIBNotifications 70005 }
        

vSTPMtp3PreferredRouteUnavailableNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "mtp3 has started to utilize a lower priority (higher cost) route to route traffic toward a given destination address, because the higher priority (lower cost) route specified for that RSP/Destination has become Unavail"
    ::= { eagleXgDsrMIBNotifications 70006 }
        

vSTPMtp3NodeIsolatedAllLinkDownNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Node isolated - All links down"
    ::= { eagleXgDsrMIBNotifications 70007 }
        

vSTPMtp3LinksetRestrictedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The SS7 linkset to an adjacent SP has restricted."
    ::= { eagleXgDsrMIBNotifications 70008 }
        

vSTPMtp3LinkCongestionNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Link Congested."
    ::= { eagleXgDsrMIBNotifications 70009 }
        

vSTPMtp3TfpReceivedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "TFP message received by mtp3 layer."
    ::= { eagleXgDsrMIBNotifications 70060 }
        

vSTPMtp3TfaReceivedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "TFA message received by MTP3 layer."
    ::= { eagleXgDsrMIBNotifications 70061 }
        

vSTPMtp3TfrReceivedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "TFR message received by MTP3 layer."
    ::= { eagleXgDsrMIBNotifications 70062 }
        

vSTPMtp3TfcReceivedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "TFC message received by MTP3 layer."
    ::= { eagleXgDsrMIBNotifications 70063 }
        

vSTPMtp3RoutingFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message was discarded due to a routing error."
    ::= { eagleXgDsrMIBNotifications 70064 }
        

vSTPMtp3RoutingFailureInvalidNiNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message was discarded due to a routing error - the NI value received in a message from the network is not assigned to the MP."
    ::= { eagleXgDsrMIBNotifications 70065 }
        

vSTPMtp3RoutingFailureInvalidSiNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message was discarded due to a routing error - the SI value received in a message from the network is associated with a User Part that is not currently supported."
    ::= { eagleXgDsrMIBNotifications 70066 }
        

vSTPVstpTxConnQueueCongestedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "VSTP egress connection message queue utilization threshold crossed."
    ::= { eagleXgDsrMIBNotifications 70101 }
        

vSTPVstpRxLinkTpsNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "VSTP ingress link MSU TPS threshold crossed"
    ::= { eagleXgDsrMIBNotifications 70102 }
        

vSTPVstpTxLinkTpsNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "VSTP egress link MSU TPS threshold crossed."
    ::= { eagleXgDsrMIBNotifications 70103 }
        

vSTPVstpRxMgmtLinkTpsNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "VSTP ingress link TPS threshold crossed for Network management messages"
    ::= { eagleXgDsrMIBNotifications 70104 }
        

vSTPVstpTxDiscardLevelNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "VSTP egress connection message is discard threshold crossed."
    ::= { eagleXgDsrMIBNotifications 70105 }
        

vSTPVstpPduBufferPoolUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the VSTP MP's PDU buffer pool is approaching its maximum capacity."
    ::= { eagleXgDsrMIBNotifications 70106 }
        

vSTPVstpSccpStackEventQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the VSTP MP's SCCP Stack Event Queue is approaching its maximum capacity."
    ::= { eagleXgDsrMIBNotifications 70107 }
        

vSTPVstpM3rlStackEventQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the VSTP MP's M3RL Stack Event Queue is approaching its maximum capacity."
    ::= { eagleXgDsrMIBNotifications 70108 }
        

vSTPVstpM3rlNetMgmtEventQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the VSTP MP's M3RL Network Management Event Queue is approaching its maximum capacity."
    ::= { eagleXgDsrMIBNotifications 70109 }
        

vSTPVstpM3uaStackEventQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the VSTP MP's Stack Event Queue is approaching its maximum capacity."
    ::= { eagleXgDsrMIBNotifications 70110 }
        

vSTPVstpM2paStackEventQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the VSTP MP's M2PA Stack Event Queue is approaching its maximum capacity."
    ::= { eagleXgDsrMIBNotifications 70111 }
        

vSTPVstpM3uaTxStackEventQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the VSTP MP's M3UA Tx Stack Event Queue is approaching its maximum capacity."
    ::= { eagleXgDsrMIBNotifications 70112 }
        

vSTPVstpIsupStackEventQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the VSTP MP's ISUP Stack Event Queue is approaching its maximum capacity."
    ::= { eagleXgDsrMIBNotifications 70113 }
        

vSTPVstpMTP2StackEventQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the VSTP MP's Mtp2 Stack Event Queue is approaching its maximum capacity."
    ::= { eagleXgDsrMIBNotifications 70114 }
        

vSTPM3rlLinksetBufferUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the VSTP MP's M3RL Linkset Buffer is approaching its maximum capacity."
    ::= { eagleXgDsrMIBNotifications 70081 }
        

vSTPM3rlRspBufferUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the VSTP MP's M3RL Rsp Buffer is approaching its maximum capacity."
    ::= { eagleXgDsrMIBNotifications 70082 }
        

vSTPSfappEventQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the VSTP MP's SFAPP Event Queue is approaching its maximum capacity."
    ::= { eagleXgDsrMIBNotifications 70301 }
        

vSTPLinkOpStateChangedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "M2PA link operational state changed"
    ::= { eagleXgDsrMIBNotifications 70201 }
        

vSTPVstpMsuFailedMTPScrNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MSU Failed MTP Screening"
    ::= { eagleXgDsrMIBNotifications 70392 }
        

vSTPInvalidMsgForAftDstnNsfiNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Invalid MSU received for AFTDSTN NSFI"
    ::= { eagleXgDsrMIBNotifications 70393 }
        

vSTPInvalidMsgForAftPcNsfiNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Invalid MSU received for AFTPC NSFI"
    ::= { eagleXgDsrMIBNotifications 70394 }
        

vSTPInvalidMsgForAftPcSsnNsfiNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Invalid MSU received for AFTPCSSN NSFI"
    ::= { eagleXgDsrMIBNotifications 70395 }
        

vSTPLinkFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "M2PA link failed"
    ::= { eagleXgDsrMIBNotifications 70202 }
        

vSTPIngressMessageDiscardedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "M2PA Ingress message discarded"
    ::= { eagleXgDsrMIBNotifications 70203 }
        

vSTPEgressMessageDiscardedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "M2PA Egress message discarded"
    ::= { eagleXgDsrMIBNotifications 70204 }
        

vSTPMessageEncodeFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message Encoding Failed"
    ::= { eagleXgDsrMIBNotifications 70205 }
        

vSTPMessageDecodeFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message Decoding Failed"
    ::= { eagleXgDsrMIBNotifications 70206 }
        

vSTPProvingTimerExpiredNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "M2pa Proving Period Timer Expired."
    ::= { eagleXgDsrMIBNotifications 70207 }
        

vSTPRemoteCongTimerExpiredNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "M2pa Remote Congestion Timer(T6) Expired."
    ::= { eagleXgDsrMIBNotifications 70208 }
        

vSTPRpoReceivedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Received Remote Processor Outage."
    ::= { eagleXgDsrMIBNotifications 70209 }
        

vSTPRemoteOOSReceivedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Received Remote Out Of Service."
    ::= { eagleXgDsrMIBNotifications 70210 }
        

vSTPSubSystemCongestedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Subsystem Congested."
    ::= { eagleXgDsrMIBNotifications 70251 }
        

vSTPSubSystemProhibitedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Subsystem Prohibited."
    ::= { eagleXgDsrMIBNotifications 70252 }
        

vSTPDuplicateActionInhibitNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "GTT Duplicate Action processing stopped."
    ::= { eagleXgDsrMIBNotifications 70286 }
        

vSTPSccpInvalidMessageReceivedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SCCP Received Invalid Message."
    ::= { eagleXgDsrMIBNotifications 70271 }
        

vSTPSccpTranslationFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SCCP Message Translation Failed."
    ::= { eagleXgDsrMIBNotifications 70272 }
        

vSTPSccpMessageRoutingFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SCCP Message Routing Failed."
    ::= { eagleXgDsrMIBNotifications 70273 }
        

vSTPScmgMessageInvalidNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SCMG Message Invalid."
    ::= { eagleXgDsrMIBNotifications 70274 }
        

vSTPGttSccpLoopDetectedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "GTT SCCP Loop Detected."
    ::= { eagleXgDsrMIBNotifications 70275 }
        

vSTPGttLoadSharingFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "GTT Load Sharing Failed."
    ::= { eagleXgDsrMIBNotifications 70276 }
        

vSTPVstpGTTActionDiscardedMSUNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "GTT Action Discarded MSU"
    ::= { eagleXgDsrMIBNotifications 70277 }
        

vSTPVstpGTTActionFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "GTT Action Failed"
    ::= { eagleXgDsrMIBNotifications 70278 }
        

vSTPVstpGTTMbrDupSetTypeFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "GTT MBR Duplicate Set Type Failed."
    ::= { eagleXgDsrMIBNotifications 70279 }
        

vSTPVstpGTTMbrDupSetTypeWarningNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "GTT MBR Duplicate Set Type Warning."
    ::= { eagleXgDsrMIBNotifications 70280 }
        

vSTPVstpGTTFlobrDupSetNameFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "GTT FLOBR Duplicate Set Name Failed."
    ::= { eagleXgDsrMIBNotifications 70281 }
        

vSTPVstpGTTFlobrDupSetNameWarningNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "GTT FLOBR Duplicate Set Name Warning."
    ::= { eagleXgDsrMIBNotifications 70282 }
        

vSTPVstpGTTFlobrMaxSearchDepthFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "GTT FLOBR Max Search Depth Failed."
    ::= { eagleXgDsrMIBNotifications 70283 }
        

vSTPVstpGTTFlobrMaxSearchDepthWarningNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "GTT FLOBR Max Search Depth Warning."
    ::= { eagleXgDsrMIBNotifications 70284 }
        

vSTPVstpMBRDecodeFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MBR Decoding Failed."
    ::= { eagleXgDsrMIBNotifications 70285 }
        

vSTPVstpXudtUdtConversionFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Message Conversion Failure of XUDT(S) to UDT(S) and vice versa at MTP3 Routing"
    ::= { eagleXgDsrMIBNotifications 70291 }
        

vSTPVstpSccpEncodeFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SCCP Encode Failure."
    ::= { eagleXgDsrMIBNotifications 70292 }
        

vSTPSfappDcdErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SFAPP Decode Error"
    ::= { eagleXgDsrMIBNotifications 70293 }
        

vSTPSfappTIDNotFoundNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SFAPP Validation Matching State not found"
    ::= { eagleXgDsrMIBNotifications 70294 }
        

vSTPSfappEcdErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SFAPP Validation Encoding Error"
    ::= { eagleXgDsrMIBNotifications 70295 }
        

vSTPSfappRspTimeoutNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SFAPP Validation Response Timeout Error"
    ::= { eagleXgDsrMIBNotifications 70296 }
        

vSTPSfappThreshExcdNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SFAPP Validation Velocity Checkk Failed."
    ::= { eagleXgDsrMIBNotifications 70297 }
        

vSTPSfappValidationFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SFAPP Validation Failed."
    ::= { eagleXgDsrMIBNotifications 70298 }
        

vSTPSfappInvalidCCNDCreceivedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Invalid CC or NDC received."
    ::= { eagleXgDsrMIBNotifications 70299 }
        

vSTPVstpUpdationFailedinUDRNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Sfapp Updation failed in UDR"
    ::= { eagleXgDsrMIBNotifications 70300 }
        

vSTPVstpMpLeaderGoActiveNotificationNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Vstp has received a notification from HA that the Maintenance Leader resource should transition to the Active role."
    ::= { eagleXgDsrMIBNotifications 70351 }
        

vSTPVstpMpLeaderGoOOSNotificationNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Vstp has received a notification from HA that the Maintenance Leader resource should transition to the OOS role."
    ::= { eagleXgDsrMIBNotifications 70352 }
        

vSTPVstpRoutingDbInconsistencyExistsNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Vstp routing db inconsistencies exist among the DA-MPs in the DSR signaling NE."
    ::= { eagleXgDsrMIBNotifications 70353 }
        

vSTPVstpTblMonCbOnLogOverrunNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "VSTP DB Table Monitoring Overrun has occurred. The eagleXgDsr update sync log used by DB Table monitoring to synchronize routing db among all DA-MP RT-DBs has overrun. The VSTP-MPs routing db sharing table is automatically audited and re-synced to correct any inconsistencies."
    ::= { eagleXgDsrMIBNotifications 70354 }
        

vSTPVstpSldbMonAbnormalErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "An unexpected error occurred during DB Table Monitoring."
    ::= { eagleXgDsrMIBNotifications 70355 }
        

vSTPPeerMPUnavlblOrCngstedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Egress STP MP is Unavailable or Congested."
    ::= { eagleXgDsrMIBNotifications 70356 }
        

vSTPNoVstpMpLeaderDetectedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "No VSTP-MP Leader Detected."
    ::= { eagleXgDsrMIBNotifications 70371 }
        

vSTPMultipleVstpMpLeadersDetectedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Multiple VSTP-MP Leader Detected."
    ::= { eagleXgDsrMIBNotifications 70372 }
        

vSTPConnectionAlarmAggregationThresholdReachedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Connection Alarm Aggregation Threshold Reached."
    ::= { eagleXgDsrMIBNotifications 70373 }
        

vSTPLinkAlarmAggregationThresholdReachedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Link Alarm Aggregation Threshold Reached."
    ::= { eagleXgDsrMIBNotifications 70374 }
        

vSTPLinksetAlarmAggregationThresholdReachedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Linkset Alarm Aggregation Threshold Reached."
    ::= { eagleXgDsrMIBNotifications 70375 }
        

vSTPRouteAlarmAggregationThresholdReachedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Route Alarm Aggregation Threshold Reached."
    ::= { eagleXgDsrMIBNotifications 70376 }
        

vSTPRspAlarmAggregationThresholdReachedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "RSP Alarm Aggregation Threshold Reached."
    ::= { eagleXgDsrMIBNotifications 70377 }
        

vSTPSltcFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SLTC Failure."
    ::= { eagleXgDsrMIBNotifications 70378 }
        

vSTPUnexpectedTfaReceivedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Unexpected TFA Received."
    ::= { eagleXgDsrMIBNotifications 70379 }
        

vSTPUnexpectedTfrReceivedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Unexpected TFR Received."
    ::= { eagleXgDsrMIBNotifications 70380 }
        

vSTPUnexpectedTfpReceivedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Unexpected TFP Received."
    ::= { eagleXgDsrMIBNotifications 70381 }
        

vSTPUnexpectedTfcReceivedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Unexpected TFC Received."
    ::= { eagleXgDsrMIBNotifications 70382 }
        

vSTPInvalidH0H1CodeNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Invalid H0 H1 Code."
    ::= { eagleXgDsrMIBNotifications 70383 }
        

vSTPTfcGeneratedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "TFC Generated."
    ::= { eagleXgDsrMIBNotifications 70384 }
        

vSTPCOOPerformedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Change Over Order Performed."
    ::= { eagleXgDsrMIBNotifications 70385 }
        

vSTPECOPerformedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Emergency Change Over Performed."
    ::= { eagleXgDsrMIBNotifications 70386 }
        

vSTPCbTimerExpiredNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Changeback Timer Expired."
    ::= { eagleXgDsrMIBNotifications 70387 }
        

vSTPUpuReceivedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "UPU Received."
    ::= { eagleXgDsrMIBNotifications 70388 }
        

vSTPVstpSCCPAppMSUDiscardedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SCCP Application MSU Discarded."
    ::= { eagleXgDsrMIBNotifications 70416 }
        

vSTPVstpmtp3LoopDetectedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MTP3 Circular Loop Detected."
    ::= { eagleXgDsrMIBNotifications 70410 }
        

vSTPVstpDfltMccNotDfnNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Default value of MCC is not defined"
    ::= { eagleXgDsrMIBNotifications 70501 }
        

vSTPVstpDfltMncNotDfnNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Default value of MNC is not defined"
    ::= { eagleXgDsrMIBNotifications 70502 }
        

vSTPVstpUdrDbServStateChangeNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "STP UDR DB Service State Changed"
    ::= { eagleXgDsrMIBNotifications 70068 }
        

vSTPVstpEirTcapDecodeErrNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Failed to decode TCAP parameter"
    ::= { eagleXgDsrMIBNotifications 70069 }
        

vSTPVstpEirEncodeFailNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Eir Message Encode failed"
    ::= { eagleXgDsrMIBNotifications 70070 }
        

vSTPVstpMissingImeiNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "IMEI is missing in the received message"
    ::= { eagleXgDsrMIBNotifications 70071 }
        

vSTPVstpInvalidImeiNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Invalid Length for Map IMEI Parameter"
    ::= { eagleXgDsrMIBNotifications 70072 }
        

vSTPVstpUnkMessageNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Unsupported TCAP message type      "
    ::= { eagleXgDsrMIBNotifications 70073 }
        

vSTPVstpLssEventQueueNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the VSTP MP's LSS Stack Event Queue is approaching its maximum capacity."
    ::= { eagleXgDsrMIBNotifications 70075 }
        

vSTPVstpLssLoggingEventQueueNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the VSTP MP's Logging Stack Event Queue is approaching its maximum capacity."
    ::= { eagleXgDsrMIBNotifications 70076 }
        

vSTPVstpEirApplLogFetchErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Vstp Eir Log File fetching from MP failed"
    ::= { eagleXgDsrMIBNotifications 70077 }
        

vSTPVstpEirLogErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Vstp Eir error in logging equipment status to log file in MP"
    ::= { eagleXgDsrMIBNotifications 70078 }
        

vSTPM2paRetransmissionBufferUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the VSTP MPs M2PA Retransmission Buffer Buffer is approaching its maximum capacity."
    ::= { eagleXgDsrMIBNotifications 70083 }
        

vSTPMtp2TransmissionBufferUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the VSTP MPs MTP2 Transmission and Retransmission Buffer is approaching its maximum capacity."
    ::= { eagleXgDsrMIBNotifications 70084 }
        

vSTPVstpSrvcInvDgtLenNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MNP length of the conditioned digit is invalid"
    ::= { eagleXgDsrMIBNotifications 70302 }
        

vSTPVstpSrvcDfltCcNotDfnNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Dflt CC not defined"
    ::= { eagleXgDsrMIBNotifications 70505 }
        

vSTPVstpSrvcDfltNcNotDfnNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "dflt NC not defined"
    ::= { eagleXgDsrMIBNotifications 70504 }
        

vSTPVstpGportLoopDetectedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "NP Circular Route detected"
    ::= { eagleXgDsrMIBNotifications 70304 }
        

vSTPVstpPcTypeAnsiNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MNP translated PC type is ANSI"
    ::= { eagleXgDsrMIBNotifications 70305 }
        

vSTPVstpInvMsisdnDgtNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "GPORT inv map msisdn for sri/srism"
    ::= { eagleXgDsrMIBNotifications 70306 }
        

vSTPVstpSrvcInvPrefxLenNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Too many digits"
    ::= { eagleXgDsrMIBNotifications 70307 }
        

vSTPVstpSrvcXlatedPcIsVstpTpcNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MNP Xlated to vSTP TPC"
    ::= { eagleXgDsrMIBNotifications 70308 }
        

vSTPVstpSccpRtnXingDomainNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MNP CGPA GTA xlation is crossing domain"
    ::= { eagleXgDsrMIBNotifications 70309 }
        

vSTPVstpGflexNoImsiNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "G-Flex MLR Op without IMSI erroneous"
    ::= { eagleXgDsrMIBNotifications 70321 }
        

vSTPVstpGflexNoImsiSkipNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "G-Flex MLR Op without IMSI skipped"
    ::= { eagleXgDsrMIBNotifications 70322 }
        

vSTPVstpGflexBadTcapNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "G-Flex MLR Op with bad TCAP skipped"
    ::= { eagleXgDsrMIBNotifications 70323 }
        

vSTPVstpGflexInvImsiNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "G-Flex MLR Op with bad IMSI skipped"
    ::= { eagleXgDsrMIBNotifications 70324 }
        

vSTPVstpGflexInvMsisdnNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "G-Flex MLR Op with bad MSISDN skipped"
    ::= { eagleXgDsrMIBNotifications 70325 }
        

vSTPVstpGflexInvImsiMsisdnNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "G-Flex MLR Op without IMSI or MSISDN skipped"
    ::= { eagleXgDsrMIBNotifications 70326 }
        

vSTPVstpGflexE214ConversionNotPossibleNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "G-Flex E214 Conversion Not Possible"
    ::= { eagleXgDsrMIBNotifications 70327 }
        

vSTPVstpAICdTtMismatchNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "ANSI to ITU CDPA GT Conversion Failure"
    ::= { eagleXgDsrMIBNotifications 70400 }
        

vSTPVstpAICgTtMismatchNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "ANSI to ITU CGPA GT Conversion Failure"
    ::= { eagleXgDsrMIBNotifications 70401 }
        

vSTPVstpIACdTtMismatchNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "ITU to ANSI CDPA GT Conversion Failure"
    ::= { eagleXgDsrMIBNotifications 70402 }
        

vSTPVstpIACgTtMismatchNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "ITU to ANSI CGPA GT Conversion Failure"
    ::= { eagleXgDsrMIBNotifications 70403 }
        

vSTPVstpAftPcCnvFailNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Affected PC Conversion Failure"
    ::= { eagleXgDsrMIBNotifications 70404 }
        

vSTPVstpM3rlOpcCnvFailNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "OPC conversion failed"
    ::= { eagleXgDsrMIBNotifications 70405 }
        

vSTPVstpCgPcAlsUndefinedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Conversion failed. CGPA PC alias undefined."
    ::= { eagleXgDsrMIBNotifications 70406 }
        

vSTPVstpInvMsgLengthNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Conversion MSU discard. SCCP MSU too large"
    ::= { eagleXgDsrMIBNotifications 70407 }
        

vSTPVstpInvSegParLengthNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Conversion MSU discard. Invalid segmentation parameters"
    ::= { eagleXgDsrMIBNotifications 70408 }
        

vSTPVstpInvSccpEleLenErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Conversion Failed. Incorrect SCCP parameter length."
    ::= { eagleXgDsrMIBNotifications 70409 }
        

vSTPVstpInvScmgMsgTypeNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Conversion MSU discard. Invalid SCMG msg type"
    ::= { eagleXgDsrMIBNotifications 70411 }
        

vSTPVstpInvAcnLenNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Unsupported ACN object ID length."
    ::= { eagleXgDsrMIBNotifications 70420 }
        

vSTPVstpFailtoDecodeInapParamNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Failed to Decode TCAP parameters."
    ::= { eagleXgDsrMIBNotifications 70421 }
        

vSTPVstpInapCdpaMissingNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "INAP Called Party Number is missing."
    ::= { eagleXgDsrMIBNotifications 70422 }
        

vSTPVstpVlrStatusChangedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "VlR Status changed"
    ::= { eagleXgDsrMIBNotifications 70429 }
        

vSTPVstpDynVeloThreshCrossedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Velocity Threshold Crossed"
    ::= { eagleXgDsrMIBNotifications 70430 }
        

vSTPVstpDynVLRProfAgingNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Dynamic VLR Profile Aging"
    ::= { eagleXgDsrMIBNotifications 70431 }
        

vSTPVstpDynVLRRoamAgingNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Dynamic VLR Roaming Aging"
    ::= { eagleXgDsrMIBNotifications 70432 }
        

vSTPVstpVlrDynLearningOFFNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Vstp Dynamic learning is turned OFF"
    ::= { eagleXgDsrMIBNotifications 70433 }
        

vSTPVstpVlrDynLearningLearntimerNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Vstp Dynamic learning LEARN Mode Timer Expired"
    ::= { eagleXgDsrMIBNotifications 70434 }
        

vSTPVstpVlrDynProfileTableFullNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Vstp Dynamic Profile Table is Full"
    ::= { eagleXgDsrMIBNotifications 70435 }
        

vSTPVstpVlrDynRoamingTableFullNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Vstp Dynamic Roaming Table is Full"
    ::= { eagleXgDsrMIBNotifications 70436 }
        

vSTPVstpMissingMandatoryParmNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Mandatory Parameter is missing in the received message"
    ::= { eagleXgDsrMIBNotifications 70091 }
        

vSTPVstpMalformedSubIdNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Malformed Subscriber Id Parameter"
    ::= { eagleXgDsrMIBNotifications 70092 }
        

vSTPVstpUnexpectedSubIdNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Uexpected Subscriber Id Parameter value"
    ::= { eagleXgDsrMIBNotifications 70093 }
        

vSTPVstpInvalidMsisdnNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Invalid Length for MSISDN value in Subscriber Identinty  Parameter"
    ::= { eagleXgDsrMIBNotifications 70094 }
        

vSTPVstpInvalidRequestedInfoNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Invalid Requested Info Parameter in the ATI query message"
    ::= { eagleXgDsrMIBNotifications 70095 }
        

vSTPVstpDigitsTruncatedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Digits truncated in encoded parameter in response msg"
    ::= { eagleXgDsrMIBNotifications 70096 }
        

vSTPVstpSccpEgressTpsThresholdNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Sccp Egress Tps Threshold Crossed."
    ::= { eagleXgDsrMIBNotifications 70418 }
        

vSTPVstpSfappStackEventQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the VSTP MPs SFAPP Stack Event Queue is approaching its maximum capacity."
    ::= { eagleXgDsrMIBNotifications 70503 }
        

vSTPVstpTooManyDigitDRANotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DRA digits have exceeded INAP_MAX_CDPN_DIGITS (32)"
    ::= { eagleXgDsrMIBNotifications 70310 }
        

vSTPVstpIdprCgpnEcdErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Failed to encode the CGPN for IDPR Feature"
    ::= { eagleXgDsrMIBNotifications 70311 }
        

vSTPVstpIdprCdpnEcdErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Failed to encode the CDPN for IDPR Feature"
    ::= { eagleXgDsrMIBNotifications 70312 }
        

vSTPVstpIdprCdpnNppServiceOffNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "IDPRCDPN(X) NPP SERVICE is OFF"
    ::= { eagleXgDsrMIBNotifications 70313 }
        

vSTPVstpIdprCgpnNppServiceOffNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "IDPRCGPN NPP SERVICE is OFF"
    ::= { eagleXgDsrMIBNotifications 70314 }
        

vSTPVstpDestAddrDcdFailNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DESTINATION ADDRESS DECODING is FAIL"
    ::= { eagleXgDsrMIBNotifications 70315 }
        

vSTPVstpTcapEncFailNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "TCAP ENCODING is FAIL"
    ::= { eagleXgDsrMIBNotifications 70316 }
        

vSTPVstpOutBoundDigitNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "OUT OF BOUND DIGIT"
    ::= { eagleXgDsrMIBNotifications 70317 }
        

vSTPVstpSMSMandParamMissNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SMS MANDATORY PARAMETER MISSING"
    ::= { eagleXgDsrMIBNotifications 70318 }
        

vSTPVstpAddrDcdFailNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "ADDRESS DECODING is FAIL"
    ::= { eagleXgDsrMIBNotifications 70319 }
        

vSTPVstpMnpCdpaMatchHomeSmscNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MNPCDPA MATCHES HOME SMSC"
    ::= { eagleXgDsrMIBNotifications 70320 }
        

vSTPMtp2LinkAdmStateChangeNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MTP2 Link admin state change"
    ::= { eagleXgDsrMIBNotifications 70220 }
        

vSTPMtp2FailedToSendMsgNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Failed to send message to TDM driver"
    ::= { eagleXgDsrMIBNotifications 70221 }
        

vSTPMtp2FailedToRcvMsgNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Failed to receive message from TDM driver"
    ::= { eagleXgDsrMIBNotifications 70222 }
        

vSTPMtp2LinkOpStateChangeNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MTP2 link operational state changed"
    ::= { eagleXgDsrMIBNotifications 70223 }
        

vSTPMtp2LinkFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MTP2 link failed"
    ::= { eagleXgDsrMIBNotifications 70224 }
        

vSTPMtp2IngressMsgDiscardedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MTP2 Ingress message discarded"
    ::= { eagleXgDsrMIBNotifications 70225 }
        

vSTPMtp2EgressMsgDiscardedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MTP2 Egress message discarded"
    ::= { eagleXgDsrMIBNotifications 70226 }
        

vSTPMtp2RemoteOOSReceivedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Received Remote Out Of Service on MTP2 link."
    ::= { eagleXgDsrMIBNotifications 70227 }
        

vSTPMtp2RpoReceivedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Received Remote Processor Outage on MTP2 link."
    ::= { eagleXgDsrMIBNotifications 70228 }
        

vSTPVstpTifUnexpectedSiNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "TIF Stop Action can process only ISUP SI=5 MSU"
    ::= { eagleXgDsrMIBNotifications 70423 }
        

vSTPVstpTifRouteFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SIF size exceeds 272 byte limit"
    ::= { eagleXgDsrMIBNotifications 70424 }
        

vSTPVstpIsupDcdFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "ISUP IAM decode failed"
    ::= { eagleXgDsrMIBNotifications 70425 }
        

vSTPVstpIsupDcdCdpaFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "ISUP IAM Cld Pty decode failed"
    ::= { eagleXgDsrMIBNotifications 70426 }
        

vSTPVstpIsupEcdFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "ISUP encode failed"
    ::= { eagleXgDsrMIBNotifications 70427 }
        

vSTPVstpTifCcMismatchDnNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "TIF CgPN NS Failure: CC mismatch in DN"
    ::= { eagleXgDsrMIBNotifications 70428 }
        

vSTPSccpXUDTReassemblyFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SCCP XUDT Reassembly Failure"
    ::= { eagleXgDsrMIBNotifications 70331 }
        

vSTPSccpXUDTSegmentationFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SCCP XUDT Segmentation Failure"
    ::= { eagleXgDsrMIBNotifications 70332 }
        

vSTPVstpTobrDupOpcodeFoundDiscardNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "GTT TOBR Dup Opcode MSU discarded"
    ::= { eagleXgDsrMIBNotifications 70441 }
        

vSTPVstpTobrMulCompTransFoundNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "GTT TOBR Multiple Comp: Translation Found."
    ::= { eagleXgDsrMIBNotifications 70442 }
        

vSTPVstpTobrMulCompTransNaDiscardNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "GTT TCAPMulComp Translation Not Allowed."
    ::= { eagleXgDsrMIBNotifications 70443 }
        

vSTPVstpTobrMulCompMaxcompExceededNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "GTT TCAPMulComp Max Components Exceeded."
    ::= { eagleXgDsrMIBNotifications 70444 }
        

vSTPVstpGTTActionSetTestModeOnNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SCCP GTTAction Set Testmode parameter ON"
    ::= { eagleXgDsrMIBNotifications 70445 }
        

vSTPVstpSecuLogEventQueueNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the VSTP MP's Security Logging Stack Event Queue is approaching its maximum capacity."
    ::= { eagleXgDsrMIBNotifications 70437 }
        

vSTPVstpSecuLogErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Vstp error in logging security logs to csv file in MP"
    ::= { eagleXgDsrMIBNotifications 70438 }
        

vSTPVstpSecuLogFetchErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Vstp Security Log File fetching from MP failed"
    ::= { eagleXgDsrMIBNotifications 70439 }
        

vSTPVstpSecuLogRemoteServerErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Vstp Security Log File fetching from Active SO to Remote Server failed"
    ::= { eagleXgDsrMIBNotifications 70440 }
        

vSTPVstpRxMpTpsNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "VSTP ingress max Mp MSU TPS threshold crossed"
    ::= { eagleXgDsrMIBNotifications 70357 }
        

vSTPVstpTxMpTpsNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "VSTP egress Max Mp MSU TPS threshold crossed."
    ::= { eagleXgDsrMIBNotifications 70358 }
        

vSTPVstpServiceStackEventQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the VSTP MPs Service Stack Event Queue is approaching its maximum capacity."
    ::= { eagleXgDsrMIBNotifications 70446 }
        

vSTPServiceMpUnavailableNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Service MP not available, can't send message to Service Mp"
    ::= { eagleXgDsrMIBNotifications 70451 }
        

vSTPSmsProxyValidationFailedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Service Validation Failed."
    ::= { eagleXgDsrMIBNotifications 70447 }
        

vSTPSmsProxyValRspTimeoutNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Service Validation Response Timeout Error"
    ::= { eagleXgDsrMIBNotifications 70448 }
        

vSTPSmsProxyEcdErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Service Validation Encoding Error"
    ::= { eagleXgDsrMIBNotifications 70449 }
        

vSTPSmsProxyDcdErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Service Validation Decoding Error"
    ::= { eagleXgDsrMIBNotifications 70450 }
        

vSTPSmsProxyAllowlistNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SMSC GTA is Allowed "
    ::= { eagleXgDsrMIBNotifications 70452 }
        

vSTPSmsProxyBlocklistNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SMSC GTA is Blocked"
    ::= { eagleXgDsrMIBNotifications 70453 }
        

vSTPSmsProxySccpValidFailNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "SCCP Validation failed in Service MP due to inconsistency between sccp cdpa and tcap smrpda"
    ::= { eagleXgDsrMIBNotifications 70454 }
        

vSTPSmsProxyMtfsmInvkTimeoutNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MTFSM Invoke Timer waits for MTFSM message and on timeout raises this event"
    ::= { eagleXgDsrMIBNotifications 70455 }
        

vSTPSmsProxyDosInvkTimeoutNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "DOS Timer waits for Delivery Report SM message and on timeout raises this event"
    ::= { eagleXgDsrMIBNotifications 70456 }
        

vSTPVstpTcapDecodeErrNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MSU Discarded on TCAP Decode Error."
    ::= { eagleXgDsrMIBNotifications 70457 }
        

vSTPSmsProxyAckTransNotFndNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Ack Message for which Transaction are not found in both Originator and Termination Side at Service MP"
    ::= { eagleXgDsrMIBNotifications 70458 }
        

vSTPPctMsuDiscardNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "MSU discarded after successful PCT DPC Lookup due to DPC unavailability"
    ::= { eagleXgDsrMIBNotifications 70459 }
        

vSTPFailedToCreatePcapngFileNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Failed to create pcapng file"
    ::= { eagleXgDsrMIBNotifications 70478 }
        

vSTPTracingLayerCongestionNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Congestion at Tracing Layer."
    ::= { eagleXgDsrMIBNotifications 70479 }
        

vSTPTraceIdDisabledNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Trace Id Disabled"
    ::= { eagleXgDsrMIBNotifications 70480 }
        

vSTPVstpTracingStackEventQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the VSTP MP tracing Stack Event Queue is approaching its maximum capacity."
    ::= { eagleXgDsrMIBNotifications 70481 }
        

vSTPVstpTraceOamStackEventQueueUtilNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The percent utilization of the VSTP Traceoam Stack Event Queue is approaching its maximum capacity."
    ::= { eagleXgDsrMIBNotifications 70482 }
        



measStreamMeasStreamBrokerConnectFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Connection to Kafka Broker is failing."
    ::= { eagleXgDsrMIBNotifications 72000 }
        

measStreamMeasStreamSendFailureNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Measurement data send to Kafka failed."
    ::= { eagleXgDsrMIBNotifications 72001 }
        

measStreamMeasStreamTransferTimeExceededNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Measurement data transfer could not be completed within interval."
    ::= { eagleXgDsrMIBNotifications 72002 }
        

measStreamMeasStreamParsingErrorNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Error while collecting,parsing metrices."
    ::= { eagleXgDsrMIBNotifications 72003 }
        




cOHIdihIngressRateNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "The Idih Kafka Ingress Json Stack Event Rate is approaching its defined threshold capacity."
    ::= { eagleXgDsrMIBNotifications 73001 }
        

cOHKafkaQueueCongestedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Idih Kafka Producer Queue Congested"
    ::= { eagleXgDsrMIBNotifications 73002 }
        

cOHKafkaConnDownNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Idih Kafka Connection Down"
    ::= { eagleXgDsrMIBNotifications 73003 }
        

cOHKafkaConnDegradedNotify NOTIFICATION-TYPE
    OBJECTS { eagleXgDsrAlarmSrcNode, eagleXgDsrAlarmNumber, eagleXgDsrAlarmInstance,
              eagleXgDsrAlarmSeverity, eagleXgDsrAlarmText, eagleXgDsrAlarmInfo,
              eagleXgDsrAlarmGroup, eagleXgDsrServerHostname,
              eagleXgDsrAlarmSequence, eagleXgDsrAlarmTimestamp,
              eagleXgDsrAlarmEventType, eagleXgDsrAlarmProbableCause,
              eagleXgDsrAlarmAdditionalInfo }
    STATUS  current
    DESCRIPTION
            "Idih Kafka Connection Degraded"
    ::= { eagleXgDsrMIBNotifications 73004 }
        


END

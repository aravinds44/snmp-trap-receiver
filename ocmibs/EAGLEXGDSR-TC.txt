--
-- Copyright (C) 2006, 2014, Oracle and/or its affiliates. All rights reserved.
-- $Id$
--
EAGLEXGDSR-TC DEFINITIONS ::= BEGIN

IMPORTS
    TEXTUAL-CONVENTION FROM SNMPv2-TC;

--
-- Textual Conventions
--
EagleXgDsrNodeId ::= TEXTUAL-CONVENTION
    DISPLAY-HINT    "3x/1x"
    STATUS          current
    DESCRIPTION
            "Node ID of the EAGLEXGDSR server."
    SYNTAX  OCTET STRING (SIZE (4))

EagleXgDsrNodeCap ::= TEXTUAL-CONVENTION
    STATUS      deprecated
    DESCRIPTION
            "NodeCapability"
    SYNTAX  INTEGER {
                masterCapable(0),
                none(1)
            }

EagleXgDsrNodeCapability ::= TEXTUAL-CONVENTION
    STATUS      current
    DESCRIPTION
            "HA capability of the node"
    SYNTAX  INTEGER {
                oos(0),
                observer(1),
                spare(2),
                standby(3),
                active(4)
            }

EagleXgDsrAlarmSeverity ::= TEXTUAL-CONVENTION
    STATUS      current
    DESCRIPTION
            "Alarm severity values"
    SYNTAX  INTEGER {
                critical(1),
                major(2),
                minor(3),
                info(4),
                clear(5)
            }

EagleXgDsrAlarmNumber ::= TEXTUAL-CONVENTION
    STATUS      current
    DESCRIPTION
            "Alarm number values"
    SYNTAX  INTEGER (0..2147483647)

EagleXgDsrDateAndTime ::= TEXTUAL-CONVENTION
    DISPLAY-HINT    "2d-1d-1d,1d:1d:1d.2d"
    STATUS          current
    DESCRIPTION
            "Millisecond resolution date and time type"
    SYNTAX      OCTET STRING (SIZE (7 | 9))

EagleXgDsrTaskName ::= TEXTUAL-CONVENTION
    DISPLAY-HINT    "16a"
    STATUS          current
    DESCRIPTION
            "Process name"
    SYNTAX      OCTET STRING (SIZE (0..16))

EagleXgDsrMergePartNum ::= TEXTUAL-CONVENTION
    STATUS          current
    DESCRIPTION
            "Part number for merge tables"
    SYNTAX      INTEGER {
                    local(0),
                    merged(1),
                    localOnly(2)
                }

EagleXgDsrAlarmGroup ::= TEXTUAL-CONVENTION
    STATUS          current
    DESCRIPTION
            "Group an alarm belongs to"
    SYNTAX      OCTET STRING (SIZE (0..4))

EagleXgDsrTelemetryName ::= TEXTUAL-CONVENTION
    STATUS          current
    DESCRIPTION
            "Telemetry ID number"
    SYNTAX      OCTET STRING (SIZE (0..25))

EagleXgDsrTelemetryType ::= TEXTUAL-CONVENTION
    STATUS          current
    DESCRIPTION
            "Telemetry type"
    SYNTAX      INTEGER {
                    basic(0),
                    rate(1),
                    percent(2)
                }

EagleXgDsrTelemetrySource ::= TEXTUAL-CONVENTION
    STATUS          current
    DESCRIPTION
            "Telemetry source type"
    SYNTAX      INTEGER {
                    local(0),
                    groupAverage(1),
                    procCpu(2),
                    procCpuUser(3),
                    procCpuSys(4),
                    procMemRes(5),
                    procMemHeap(6),
                    procMemTotal(7),
                    loadAvg1(8),
                    loadAvg5(9),
                    loadAvg15(10),
                    memTotal(11),
                    memFree(12),
                    swapTotal(13),
                    swapFree(14),
                    sysCpu(15),
                    shMemTotal(16),
                    shMemFree(17),
                    sysUpTime(18),
                    diskTotal(19),
                    diskFree(20),
                    procNCpu(21),
                    procNCpuUser(22),
                    procNCpuSys(23),
                    sysCpuCore(24),
                    swapIn(25),
                    swapOut(26),
                    localAppl(27)
                }

EagleXgDsrTelemetryBasis ::= TEXTUAL-CONVENTION
    STATUS          current
    DESCRIPTION
            "Telemetry source type"
    SYNTAX      INTEGER {
                    currentValue(0),
                    runningAvg(1)
                }

EagleXgDsrTelemetryId ::= TEXTUAL-CONVENTION
    STATUS			current
    DESCRIPTION
            "Telemetry ID number"
    SYNTAX		INTEGER (0..32767)


EagleXgDsrEventType ::= TEXTUAL-CONVENTION
    STATUS          current
    DESCRIPTION
            "Event type"
    SYNTAX      INTEGER {
                    none(0),
                    communication(1),
                    qualityOfService(2),
                    processingError(3),
                    equipment(4),
                    environmental(5),
                    integrityViolation(6),
                    operationalViolation(7),
                    physicalViolation(8),
                    securityServiceOrMechanismViolation(9),
                    timeDomainViolation(10)
                }

END

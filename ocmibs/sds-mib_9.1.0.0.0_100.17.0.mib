--
-- Copyright (C) 2012, 2014, Oracle and/or its affiliates. All rights reserved.
-- $Id$
--
SDS-MIB DEFINITIONS ::= BEGIN

IMPORTS
    MODULE-IDENTITY, OBJECT-TYPE, NOTIFICATION-TYPE, Counter32, TimeTicks,
    Integer32, Unsigned32
                                                FROM SNMPv2-SMI
    TEXTUAL-CONVENTION, DisplayString, PhysAddress, TruthValue
                                                FROM SNMPv2-TC
    TimeFilter                                  FROM RMON2-MIB
    tekelecSDS                              FROM TEKELEC-TOPLEVEL-REG
    SdsNodeId,  SdsAlarmSeverity, SdsAlarmNumber, SdsDateAndTime,
    SdsTaskName, SdsMergePartNum, SdsNodeCap, SdsNodeCapability, 
    SdsAlarmGroup, SdsTelemetryName, SdsTelemetryType, SdsEventType,
    SdsTelemetrySource, SdsTelemetryBasis, SdsTelemetryId
                                                FROM SDS-TC;

sdsMIB MODULE-IDENTITY
    LAST-UPDATED "201210011308Z"
    ORGANIZATION "Tekelec, Inc."
    CONTACT-INFO
            "   Tekelec, Inc.
                5200 Paramount Parkway
                Morrisville, NC 27560
                USA

                http://www.tekelec.com/support/
                US & Canada: 888.367.8552
                India: +91.124.436.8552
                China: +65.6248.4510
                UK & Europe: +44.1784.467.804"
    DESCRIPTION
            "Updated contact information, added descriptions for all of the MIB
            variables that were missing descriptions and removed the IMPLIED
            keyword from the index to sdsSiteInfoEntry."
    REVISION    "201210011308Z"
    DESCRIPTION
            "Added new varbind - sdsAlarmSrcName to SdsAlarmEntry
            to satisfy requirement# 1313 of PR 209807"
    REVISION    "201207311924Z"
    DESCRIPTION
            "Updated contact information."
    REVISION    "201207161413Z"
    DESCRIPTION
            "Added new table SdsSiteInfoTable to sdsSystem. 
            Added sdsServerNodeCapability, sdsServerInhibitRepPlans,
            and sdsServerSiteId to sdsNodeInfoEntry, and deprecated
            sdsServerInhibitFlag and sdsServerNodeCap."
    REVISION    "201205181730Z"
    DESCRIPTION
            "Added sdsAlarmSequence varbind and added
            sdsServerHostname, sdsAlarmSequence and
            sdsAlarmTimestamp to alarm traps.
            Updated contact information."
    REVISION    "201203301715Z"
    DESCRIPTION
            "Removed IMPLIED keyword on the alarm and telemetry tables."
    REVISION    "201111041226Z"
    DESCRIPTION
            "Updates to telemetry tables."
    REVISION    "200906291536Z"
    DESCRIPTION
            "Updates for MIB formatting compliance."
    REVISION    "200905201536Z"
    DESCRIPTION
            "The MIB module for managing SDS implementations.
             Copyright (C) Tekelec, Inc."
    ::= { tekelecSDS 1 }

--
-- MIB tables and variables definition
--
sdsMIBObjects   OBJECT IDENTIFIER ::= { sdsMIB 1 }

sdsSystem       OBJECT IDENTIFIER ::= { sdsMIBObjects 1 }

sdsServerLocalName OBJECT-TYPE
    SYNTAX      DisplayString (SIZE (0..255))
    MAX-ACCESS  read-only
    STATUS      current
    DESCRIPTION
            "The hostname of the server."
    ::= { sdsSystem 1 }

sdsServerLocalNodeId OBJECT-TYPE
    SYNTAX      SdsNodeId
    MAX-ACCESS  read-only
    STATUS      current
    DESCRIPTION
            "The node ID of the server. Each server in the topology is assigned
            a unique node ID that identifies its level, cluster number and
            member number."
    ::= { sdsSystem 2 }

sdsNodeInfoLastChangeTime OBJECT-TYPE
    SYNTAX      TimeTicks
    MAX-ACCESS  read-only
    STATUS      current
    DESCRIPTION
            "The time when the NodeInfo table last changed."
    ::= { sdsSystem 3 }

sdsNodeInfoTable OBJECT-TYPE
    SYNTAX      SEQUENCE OF SdsNodeInfoEntry
    MAX-ACCESS  not-accessible
    STATUS      current
    DESCRIPTION
            "The contents of the NodeInfo topology table containing identifying
            information about each server provisioning in the network topology."
    ::= { sdsSystem 4 }

sdsNodeInfoEntry OBJECT-TYPE
    SYNTAX      SdsNodeInfoEntry
    MAX-ACCESS  not-accessible
    STATUS      current
    DESCRIPTION
            "An entry in the NodeInfo topology table. This table is indexed by
            a node ID that is required to be unique for each server in the
            network topology."
    INDEX { IMPLIED sdsServerNodeId }
    ::= { sdsNodeInfoTable 1 }

SdsNodeInfoEntry ::=
    SEQUENCE {
        sdsServerNodeId          SdsNodeId,
        sdsServerNodeName        DisplayString,
        sdsServerHostname        DisplayString,
        sdsServerInhibitFlag     BITS,
        sdsServerNodeCap         SdsNodeCap,
        sdsServerExcludedTables  DisplayString,
        sdsServerNodeCapability  SdsNodeCapability,
        sdsServerInhibitRepPlans DisplayString,
        sdsServerSiteId          INTEGER
    }

sdsServerNodeId OBJECT-TYPE
    SYNTAX      SdsNodeId
    MAX-ACCESS  not-accessible
    STATUS      current
    DESCRIPTION
            "Unique node ID identifying the server. The node ID identifies the
            level (A, B or C), cluster ID number and member server number."
    ::= { sdsNodeInfoEntry 1 }

sdsServerNodeName OBJECT-TYPE
    SYNTAX      DisplayString
    MAX-ACCESS  read-only
    STATUS      current
    DESCRIPTION
            "Text name for a server in the network topology. This name may or
            may not match the hostname, but usually is the same as the
            hostname."
    ::= { sdsNodeInfoEntry 2 }

sdsServerHostname OBJECT-TYPE
    SYNTAX      DisplayString
    MAX-ACCESS  read-only
    STATUS      current
    DESCRIPTION
            "Hostname for a server in the network topology. This hostname
            matches the hostname of the server as configured in the operating
            system."
    ::= { sdsNodeInfoEntry 3 }

sdsServerInhibitFlag OBJECT-TYPE
    SYNTAX      BITS {
                    outOfService(0),
                    inetSync(1),
                    inetBroad(2),
                    inetMerge(3),
                    testApp(4),
                    haApp(5)
                }
    MAX-ACCESS  read-only
    STATUS      deprecated
    DESCRIPTION
            "Flag to control the level of service being provided by a server.
            No bits set means that the server is enabled for replication,
            merging/collection and high availability.

            Setting the outOfService(0) bit disables replication to this
            server, disables merging/collection from this server and sets the
            server to a forced standby high availability state. In addition,
            any alarms that may be present related to these services on this
            server are disabled.

            Setting the inetSync(1) bit disables replication to this server.

            The inetBroad(2) bit is obsolete and unused.

            The inetMerge(3) bit disables merging / collection from this
            server.

            The testApp(4) bit is used for testing purposes only and is not
            intended for end users.

            The haApp(5) bit disables high availability and causes the server
            to be placed in a forced standby state."
    ::= { sdsNodeInfoEntry 4 }

sdsServerNodeCap OBJECT-TYPE
    SYNTAX      SdsNodeCap
    MAX-ACCESS  read-only
    STATUS      deprecated
    DESCRIPTION
            "This flag controls whether the server actively participates in
            high availability or not. Normally this value should be set to
            masterCapable(0) for servers actively providing service. The
            exception is query servers where this value should be none(1)."
    ::= { sdsNodeInfoEntry 5 }

sdsServerExcludedTables OBJECT-TYPE
    SYNTAX      DisplayString
    MAX-ACCESS  read-only
    STATUS      deprecated
    DESCRIPTION
            "Space-separated list of table names excluded from database
            replication."
    ::= { sdsNodeInfoEntry 6 }

sdsServerNodeCapability OBJECT-TYPE
    SYNTAX      SdsNodeCapability
    MAX-ACCESS  read-only
    STATUS      current
    DESCRIPTION
            "Highest high availability role the server is capable of being
            assigned. Servers fully in service have this value set to active(4)
            while servers in maintenance states will have lower values set to
            limit the role the server is assigned. For example, servers in
            forced standby will have this value set to standby(3) and server in
            an out-of-service maintenance state will have this value set to
            oos(0)."
    ::= { sdsNodeInfoEntry 7 }

sdsServerInhibitRepPlans OBJECT-TYPE
    SYNTAX      DisplayString
    MAX-ACCESS  read-only
    STATUS      current
    DESCRIPTION
            "Space-separated list of database replication plans that are
            inhibited from replication to the server. Replication plans are a
            grouping of related database tables for the purpose of managing
            their replication across servers."
    ::= { sdsNodeInfoEntry 8 }

sdsServerSiteId OBJECT-TYPE
    SYNTAX      INTEGER
    MAX-ACCESS  read-only
    STATUS      current
    DESCRIPTION
            "Identification number corresponding to the site ID of the site in
            which the server is located. A site ID of 0 corresponds to
            Unspecified and indicates that no server site ID has been
            provisioned."
    ::= { sdsNodeInfoEntry 9 }

sdsSiteInfoTable OBJECT-TYPE
    SYNTAX      SEQUENCE OF SdsSiteInfoEntry
    MAX-ACCESS  not-accessible
    STATUS      current
    DESCRIPTION
            "Table containing the name and ID number of all of the sites in the
            network topology."
    ::= { sdsSystem 5 }

sdsSiteInfoEntry OBJECT-TYPE
    SYNTAX      SdsSiteInfoEntry
    MAX-ACCESS  not-accessible
    STATUS      current
    DESCRIPTION
            "An entry in the SiteInfo table. This table is indexed by a numeric
            site ID number."
    INDEX { sdsSiteId }
    ::= { sdsSiteInfoTable 1 }

SdsSiteInfoEntry ::=
    SEQUENCE {
        sdsSiteId          INTEGER,
        sdsSiteName        DisplayString
    }

sdsSiteId    OBJECT-TYPE
    SYNTAX      INTEGER (0..65535)
    MAX-ACCESS  not-accessible
    STATUS      current
    DESCRIPTION
            "Unique identification number for the site."
    ::= { sdsSiteInfoEntry 1 }

sdsSiteName  OBJECT-TYPE
    SYNTAX      DisplayString
    MAX-ACCESS  read-only
    STATUS      current
    DESCRIPTION
            "Name of the site."
    ::= { sdsSiteInfoEntry 2 }

sdsIdb          OBJECT IDENTIFIER ::= { sdsMIBObjects 2 }

sdsIdbTable OBJECT-TYPE
    SYNTAX      SEQUENCE OF SdsIdbEntry
    MAX-ACCESS  not-accessible
    STATUS      current
    DESCRIPTION
            "Table providing generic access to database table contents. Access
            is provided in such a way that database table contents are
            available as raw octets without a specific MIB needed."
    ::= { sdsIdb 1 }

sdsIdbEntry OBJECT-TYPE
    SYNTAX      SdsIdbEntry
    MAX-ACCESS  not-accessible
    STATUS      current
    DESCRIPTION
            "Entry for generic access to a database table record."
    INDEX   { sdsIdbTableId, sdsIdbSubpart, sdsIdbFragment,
              sdsIdbRecordId, sdsIdbFieldId }
    ::= { sdsIdbTable 1 }

SdsIdbEntry ::=
    SEQUENCE {
        sdsIdbTableId        Integer32,
        sdsIdbSubpart        Integer32,
        sdsIdbFragment       Integer32,
        sdsIdbRecordId       Integer32,
        sdsIdbFieldId        Integer32,
        sdsIdbData           OCTET STRING
    }

sdsIdbTableId OBJECT-TYPE
    SYNTAX      Integer32 (0..2147483647)
    MAX-ACCESS  not-accessible
    STATUS      current
    DESCRIPTION
            "Unique table identification number in the database data
            dictionary."
    ::= { sdsIdbEntry 1 }

sdsIdbSubpart OBJECT-TYPE
    SYNTAX      Integer32 (0..2147483647)
    MAX-ACCESS  not-accessible
    STATUS      current
    DESCRIPTION
            "Subpart number of the table. For tables with no subparts, this
            value will always be zero."
    ::= { sdsIdbEntry 2 }

sdsIdbFragment OBJECT-TYPE
    SYNTAX      Integer32 (0..2147483647)
    MAX-ACCESS  not-accessible
    STATUS      current
    DESCRIPTION
            "Unique database fragment identifier for the given table ID and
            subpart."
    ::= { sdsIdbEntry 3 }

sdsIdbRecordId OBJECT-TYPE
    SYNTAX      Integer32 (0..2147483647)
    MAX-ACCESS  not-accessible
    STATUS      current
    DESCRIPTION
            "Physical record ID number of a record."
    ::= { sdsIdbEntry 4 }

sdsIdbFieldId OBJECT-TYPE
    SYNTAX      Integer32 (0..2147483647)
    MAX-ACCESS  not-accessible
    STATUS      current
    DESCRIPTION
            "Field ID number of a field in a record in the table."
    ::= { sdsIdbEntry 5 }

sdsIdbData OBJECT-TYPE
    SYNTAX      OCTET STRING
    MAX-ACCESS  read-only
    STATUS      current
    DESCRIPTION
            "Raw contents of a field in a database table."
    ::= { sdsIdbEntry 6 }

sdsAlarms  OBJECT IDENTIFIER ::= { sdsMIBObjects 3 }

sdsAlarmLocalCount OBJECT-TYPE
    SYNTAX      Integer32
    MAX-ACCESS  read-only
    STATUS      current
    DESCRIPTION
            "A count of the number of alarms currently asserted on the local
            server."
    ::= { sdsAlarms 1 }

sdsAlarmMergeCount OBJECT-TYPE
    SYNTAX      Integer32
    MAX-ACCESS  read-only
    STATUS      current
    DESCRIPTION
            "A count of the number of alarms currently stored in the merged
            alarm table."
    ::= { sdsAlarms 2 }

sdsAlarmLocalLastChangeTime OBJECT-TYPE
    SYNTAX      TimeTicks
    MAX-ACCESS  read-only
    STATUS      current
    DESCRIPTION
            "A timestamp containing the last time that the local alarm table
            changed."
    ::= { sdsAlarms 3 }

sdsAlarmMergeLastChangeTime OBJECT-TYPE
    SYNTAX      TimeTicks
    MAX-ACCESS  read-only
    STATUS      current
    DESCRIPTION
            "A timestamp containing the last time that the merged alarm table
            changed."
    ::= { sdsAlarms 4 }

sdsAlarmTable OBJECT-TYPE
    SYNTAX      SEQUENCE OF SdsAlarmEntry
    MAX-ACCESS  not-accessible
    STATUS      current
    DESCRIPTION
            "A table containing details of the currently raised alarms, both
            local to the server and merged from other servers in the network
            topology."
    ::= { sdsAlarms 5 }

sdsAlarmEntry OBJECT-TYPE
    SYNTAX      SdsAlarmEntry
    MAX-ACCESS  not-accessible
    STATUS      current
    DESCRIPTION
            "A single entry in the alarm table indexed by part (local or
            merged), source node ID, alarm ID number and alarm instance
            string."
    INDEX   { sdsAlarmPart, sdsAlarmSrcNode, sdsAlarmNumber,
              sdsAlarmInstance }
    ::= { sdsAlarmTable 1 }


SdsAlarmEntry ::=
    SEQUENCE {
        sdsAlarmPart             SdsMergePartNum,
        sdsAlarmSrcNode          SdsNodeId,
        sdsAlarmNumber           SdsAlarmNumber,
        sdsAlarmInstance         DisplayString,
        sdsAlarmTimestamp        SdsDateAndTime,
        sdsAlarmGroup            SdsAlarmGroup,
        sdsAlarmSeverity         SdsAlarmSeverity,
        sdsAlarmText             DisplayString,
        sdsAlarmInfo             DisplayString,
        sdsAlarmSrcName          DisplayString,
        sdsAlarmEventType        SdsEventType,
        sdsAlarmProbableCause    DisplayString,
        sdsAlarmAdditionalInfo   DisplayString,
        sdsAlarmTrapName         DisplayString
    }

sdsAlarmPart OBJECT-TYPE
    SYNTAX      SdsMergePartNum
    MAX-ACCESS  read-only
    STATUS      current
    DESCRIPTION
            "Part number that identifies whether the alarm is a local alarm
            entry or a merged alarm entry."
    ::= { sdsAlarmEntry 1 }

sdsAlarmSrcNode OBJECT-TYPE
    SYNTAX      SdsNodeId
    MAX-ACCESS  read-only
    STATUS      current
    DESCRIPTION
            "Source node ID number of the server originating the alarm. See the
            sdsNodeInfo table for details. The source node is always all
            zeros for a local alarm and set to a valid node ID from the
            sdsNodeInfo table for merged alarms."
    ::= { sdsAlarmEntry 2 }

sdsAlarmNumber OBJECT-TYPE
    SYNTAX      SdsAlarmNumber
    MAX-ACCESS  read-only
    STATUS      current
    DESCRIPTION
            "Number identifying the specific alarm that is asserted."
    ::= { sdsAlarmEntry 3 }

sdsAlarmInstance OBJECT-TYPE
    SYNTAX      DisplayString
    MAX-ACCESS  read-only
    STATUS      current
    DESCRIPTION
            "String that supplies additional identifying information for the
            alarm. A combination of the alarm number and instance is what makes
            an alarm unique."
    ::= { sdsAlarmEntry 4 }

sdsAlarmTimestamp OBJECT-TYPE
    SYNTAX      SdsDateAndTime
    MAX-ACCESS  read-only
    STATUS      current
    DESCRIPTION
            "Timestamp when the alarm was last raised."
    ::= { sdsAlarmEntry 5 }

sdsAlarmGroup OBJECT-TYPE
    SYNTAX      SdsAlarmGroup
    MAX-ACCESS  read-only
    STATUS      current
    DESCRIPTION
            "Abbreviation indicating the category or group to which the alarm
            belongs."
    ::= { sdsAlarmEntry 6 }

sdsAlarmSeverity OBJECT-TYPE
    SYNTAX      SdsAlarmSeverity
    MAX-ACCESS  read-only
    STATUS      current
    DESCRIPTION
            "Severity of the alarm."
    ::= { sdsAlarmEntry 7 }

sdsAlarmText OBJECT-TYPE
    SYNTAX      DisplayString
    MAX-ACCESS  read-only
    STATUS      current
    DESCRIPTION
            "Text name of the alarm."
    ::= { sdsAlarmEntry 8 }

sdsAlarmInfo OBJECT-TYPE
    SYNTAX      DisplayString
    MAX-ACCESS  read-only
    STATUS      current
    DESCRIPTION
            "Additional textual alarm information to assist in
            troubleshooting."
    ::= { sdsAlarmEntry 9 }

sdsAlarmSrcName OBJECT-TYPE
    SYNTAX      DisplayString
    MAX-ACCESS  read-only
    STATUS      current
    DESCRIPTION
            "Node name of the server that originated the alarm. Refer to the
            sdsServerNodeName variable for more information."
    ::= { sdsAlarmEntry 10 }


sdsAlarmSequence OBJECT-TYPE
    SYNTAX      Unsigned32
    MAX-ACCESS  read-only
    STATUS      current
    DESCRIPTION
            "The current alarm sequence number."
    ::= { sdsAlarms 6 }

sdsAlarmEventType        OBJECT-TYPE
    SYNTAX      SdsEventType
    MAX-ACCESS  read-only
    STATUS      current
    DESCRIPTION
            "The event type of current alarm."
    ::= { sdsAlarmEntry 11 }

sdsAlarmProbableCause    OBJECT-TYPE
    SYNTAX      DisplayString
    MAX-ACCESS  read-only
    STATUS      current
    DESCRIPTION
            "The probable cause of current alarm."
    ::= { sdsAlarmEntry 12 }

sdsAlarmAdditionalInfo   OBJECT-TYPE
    SYNTAX      DisplayString
    MAX-ACCESS  read-only
    STATUS      current
    DESCRIPTION
            "Comma-separated triplets of key flag, name and value."
    ::= { sdsAlarmEntry 13 }

sdsAlarmTrapName OBJECT-TYPE
    SYNTAX      DisplayString
    MAX-ACCESS  read-only
    STATUS      current
    DESCRIPTION
            "The SNMP Trap name of current alarm."
    ::= { sdsAlarmEntry 14 }

sdsTelemetry  OBJECT IDENTIFIER ::= { sdsMIBObjects 4 }

sdsTelemetryTableLastChangeTime  OBJECT-TYPE
    SYNTAX      TimeTicks
    MAX-ACCESS  read-only
    STATUS      current
    DESCRIPTION
            "The last time any telemetry information was updated."
    ::= { sdsTelemetry 1 }

sdsTelemetryDefTable OBJECT-TYPE
    SYNTAX      SEQUENCE OF SdsTelemetryDefEntry
    MAX-ACCESS  not-accessible
    STATUS      current
    DESCRIPTION
            "Table containing the definitions of all of the telemetry data
            being collected."
    ::= { sdsTelemetry 2 }

sdsTelemetryDefEntry OBJECT-TYPE
    SYNTAX      SdsTelemetryDefEntry
    MAX-ACCESS  not-accessible
    STATUS      current
    DESCRIPTION
            "Entry for the definition of a single piece of telemetry data,
            indexed by a unique identification number."
    INDEX { sdsTelemetryDefId }
    ::= { sdsTelemetryDefTable 1 }

SdsTelemetryDefEntry ::=
    SEQUENCE {
        sdsTelemetryDefId            SdsTelemetryId,
        sdsTelemetryDefName          SdsTelemetryName,
        sdsTelemetryDefType          SdsTelemetryType,
        sdsTelemetryDefSource        SdsTelemetrySource,
        sdsTelemetryDefGroup         SdsTelemetryName,
        sdsTelemetryDefGroupWeight   Integer32,
        sdsTelemetryDefDeriveGroup   SdsTelemetryName,
        sdsTelemetryDefTotal         Unsigned32,
        sdsTelemetryDefMerged        TruthValue,
        sdsTelemetryDefSourceMeasId  INTEGER,
        sdsTelemetryDefAvgInterval   Integer32,
        sdsTelemetryDefDestMeasId1   INTEGER,
        sdsTelemetryDefDestMeasId2   INTEGER,
        sdsTelemetryDefSubNameTab    SdsTelemetryName
    }

sdsTelemetryDefId  OBJECT-TYPE
    SYNTAX      SdsTelemetryId
    MAX-ACCESS  not-accessible
    STATUS      current
    DESCRIPTION
            "Unique ID number identifying the telemetry value."
    ::= { sdsTelemetryDefEntry 1 }

sdsTelemetryDefName  OBJECT-TYPE
    SYNTAX      SdsTelemetryName
    MAX-ACCESS  read-only
    STATUS      current
    DESCRIPTION
            "Text name describing the telemetry value."
    ::= { sdsTelemetryDefEntry 2 }

sdsTelemetryDefType  OBJECT-TYPE
    SYNTAX      SdsTelemetryType
    MAX-ACCESS  read-only
    STATUS      current
    DESCRIPTION
            "Enumerated value describing the type of the telemetry value."
    ::= { sdsTelemetryDefEntry 3 }

sdsTelemetryDefSource  OBJECT-TYPE
    SYNTAX      SdsTelemetrySource
    MAX-ACCESS  read-only
    STATUS      current
    DESCRIPTION
            "Enumerated value describing the data source of the telemetry
            value."
    ::= { sdsTelemetryDefEntry 4 }

sdsTelemetryDefGroup  OBJECT-TYPE
    SYNTAX      SdsTelemetryName
    MAX-ACCESS  read-only
    STATUS      current
    DESCRIPTION
            "Text name used to group related telemetry values."
    ::= { sdsTelemetryDefEntry 5 }

sdsTelemetryDefGroupWeight  OBJECT-TYPE
    SYNTAX      Integer32
    MAX-ACCESS  read-only
    STATUS      current
    DESCRIPTION
            "Relative weight of this telemetry value within its group."
    ::= { sdsTelemetryDefEntry 6 }

sdsTelemetryDefDeriveGroup  OBJECT-TYPE
    SYNTAX      SdsTelemetryName
    MAX-ACCESS  read-only
    STATUS      current
    DESCRIPTION
            "For telemetry values calculated on a group of telemetry values,
            this value specifies the name of the group from which the telemetry
            values are derived."
    ::= { sdsTelemetryDefEntry 7 }

sdsTelemetryDefTotal  OBJECT-TYPE
    SYNTAX      Unsigned32
    MAX-ACCESS  read-only
    STATUS      current
    DESCRIPTION
            "Numeric total value for calculating percentages for percentage
            telemetry values."
    ::= { sdsTelemetryDefEntry 8 }

sdsTelemetryDefMerged  OBJECT-TYPE
    SYNTAX      TruthValue
    MAX-ACCESS  read-only
    STATUS      current
    DESCRIPTION
            "Boolean controlling whether the telemetry value is merged or not."
    ::= { sdsTelemetryDefEntry 9 }

sdsTelemetryDefSourceMeasId  OBJECT-TYPE
    SYNTAX      INTEGER
    MAX-ACCESS  read-only
    STATUS      current
    DESCRIPTION
            "Contains the measurement ID of the source measurement data for
            this telemetry value if the telemetry value is based on a
            measurement. If this telemetry value is not based on a measurement,
            it contains -1."
    ::= { sdsTelemetryDefEntry 10 }

sdsTelemetryDefAvgInterval  OBJECT-TYPE
    SYNTAX      Integer32
    MAX-ACCESS  read-only
    STATUS      current
    DESCRIPTION
            "Duration in seconds over which running average telemetry values
            are normalized."
    ::= { sdsTelemetryDefEntry 11 }

sdsTelemetryDefDestMeasId1  OBJECT-TYPE
    SYNTAX      INTEGER
    MAX-ACCESS  read-only
    STATUS      current
    DESCRIPTION
            "Contains a measurement ID of a destination measurement if the
            telemetry value is published into the measurements framework for
            inclusion in measurement reports. If not used, it contains -1."
    ::= { sdsTelemetryDefEntry 12 }

sdsTelemetryDefDestMeasId2  OBJECT-TYPE
    SYNTAX      INTEGER
    MAX-ACCESS  read-only
    STATUS      current
    DESCRIPTION
            "Contains a second measurement ID of a destination measurement if
            the telemetry value is published into the measurements framework
            for inclusion in measurement reports. If not used, it contains -1."
    ::= { sdsTelemetryDefEntry 13 }

sdsTelemetryDefSubNameTab  OBJECT-TYPE
    SYNTAX      SdsTelemetryName
    MAX-ACCESS  read-only
    STATUS      current
    DESCRIPTION
            "Contains the name of a database table used for mapping arrayed
            telemetry values into a corresponding name. For non-arrayed
            telemetry values or telemetry values that do no map arrayed values
            into names, this will be empty."
    ::= { sdsTelemetryDefEntry 14 }

sdsTelemetryThreshTable OBJECT-TYPE
    SYNTAX      SEQUENCE OF SdsTelemetryThreshEntry
    MAX-ACCESS  not-accessible
    STATUS      current
    DESCRIPTION
            "Table defining thresholds for telemetry values that, when
            exceeded, raise alarms."
    ::= { sdsTelemetry 3 }

sdsTelemetryThreshEntry OBJECT-TYPE
    SYNTAX      SdsTelemetryThreshEntry
    MAX-ACCESS  not-accessible
    STATUS      current
    DESCRIPTION
            "A single telemetry threshold entry, indexed by threshold ID,
            function and severity."
    INDEX { sdsTelemetryThreshId, sdsTelemetryThreshFunction,
            sdsTelemetryThreshSeverity }
    ::= { sdsTelemetryThreshTable 1 }

SdsTelemetryThreshEntry ::=
    SEQUENCE {
        sdsTelemetryThreshId         SdsTelemetryId,
        sdsTelemetryThreshFunction   SdsTelemetryName,
        sdsTelemetryThreshBasis      SdsTelemetryBasis,
        sdsTelemetryThreshAlarm      SdsAlarmNumber,
        sdsTelemetryThreshSeverity   SdsAlarmSeverity,
        sdsTelemetryThreshSetThreshold   Unsigned32,
        sdsTelemetryThreshClearThreshold Unsigned32,
        sdsTelemetryThreshAbateTimeMs    Unsigned32
    }

sdsTelemetryThreshId  OBJECT-TYPE
    SYNTAX      SdsTelemetryId
    MAX-ACCESS  not-accessible
    STATUS      current
    DESCRIPTION
            "ID number of the telemetry value to use for the threshold."
    ::= { sdsTelemetryThreshEntry 1 }

sdsTelemetryThreshFunction  OBJECT-TYPE
    SYNTAX      SdsTelemetryName
    MAX-ACCESS  not-accessible
    STATUS      current
    DESCRIPTION
            "The function name associated with this threshold. The function
            name appears in the instance field of any alarms raised when a
            threshold is exceeded."
    ::= { sdsTelemetryThreshEntry 2 }

sdsTelemetryThreshBasis  OBJECT-TYPE
    SYNTAX      SdsTelemetryBasis
    MAX-ACCESS  read-only
    STATUS      current
    DESCRIPTION
            "Contains the basis of the threshold -- whether the threshold is
            based upon the current or running average of the telemetry value."
    ::= { sdsTelemetryThreshEntry 3 }

sdsTelemetryThreshAlarm  OBJECT-TYPE
    SYNTAX      SdsAlarmNumber
    MAX-ACCESS  read-only
    STATUS      current
    DESCRIPTION
            "ID number of an alarm or event that will be used to raise an alarm
            or log an event when the threshold is exceeded. A value of -1
            disables alarming."
    ::= { sdsTelemetryThreshEntry 7 }

sdsTelemetryThreshSeverity OBJECT-TYPE
    SYNTAX      SdsAlarmSeverity
    MAX-ACCESS  not-accessible
    STATUS      current
    DESCRIPTION
            "Severity of the alarm or event raised when the threshold is
            exceeded."
    ::= { sdsTelemetryThreshEntry 8 }

sdsTelemetryThreshSetThreshold  OBJECT-TYPE
    SYNTAX      Unsigned32
    MAX-ACCESS  read-only
    STATUS      current
    DESCRIPTION
            "Threshold value that when reached will cause the threshold to be
            exceeded."
    ::= { sdsTelemetryThreshEntry 9 }

sdsTelemetryThreshClearThreshold  OBJECT-TYPE
    SYNTAX      Unsigned32
    MAX-ACCESS  read-only
    STATUS      current
    DESCRIPTION
            "Value that determines when the threshold abatement is reached."
    ::= { sdsTelemetryThreshEntry 10 }

sdsTelemetryThreshAbateTimeMs  OBJECT-TYPE
    SYNTAX      Unsigned32
    MAX-ACCESS  read-only
    STATUS      current
    DESCRIPTION
            "How long, in seconds, a given telemetry value must remain below
            the clear threshold before the threshold is considered abated."
    ::= { sdsTelemetryThreshEntry 11 }

sdsTelemetryTable OBJECT-TYPE
    SYNTAX      SEQUENCE OF SdsTelemetryEntry
    MAX-ACCESS  not-accessible
    STATUS      current
    DESCRIPTION
            "Table containing all of the collected telemetry data."
    ::= { sdsTelemetry 4 }

sdsTelemetryEntry OBJECT-TYPE
    SYNTAX      SdsTelemetryEntry
    MAX-ACCESS  not-accessible
    STATUS      current
    DESCRIPTION
            "A single telemetry value indexed by part (local or merged), source
            node ID, telemetry ID and telemetry sub ID (for arrayed telemetry
            values."
    INDEX { sdsTelemetryPart, sdsTelemetrySrcNode, sdsTelemetryId,
            sdsTelemetrySubId }
    ::= { sdsTelemetryTable 1 }

SdsTelemetryEntry ::=
    SEQUENCE {
        sdsTelemetryPart         SdsMergePartNum,
        sdsTelemetrySrcNode      SdsNodeId,
        sdsTelemetryId           SdsTelemetryId,
        sdsTelemetryMerged       TruthValue,
        sdsTelemetryRawValue     Unsigned32,
        sdsTelemetryRawAvg       Unsigned32,
        sdsTelemetryUpdateTime   SdsDateAndTime,
        sdsTelemetryThreshInfo   OCTET STRING,
        sdsTelemetrySubId        Integer32,
        sdsTelemetryName         SdsTelemetryName
    }

sdsTelemetryPart  OBJECT-TYPE
    SYNTAX      SdsMergePartNum
    MAX-ACCESS  not-accessible
    STATUS      current
    DESCRIPTION
            "Part number that identifies whether the telemetry value is a local
            value or a merged value."
    ::= { sdsTelemetryEntry 1 }

sdsTelemetrySrcNode  OBJECT-TYPE
    SYNTAX      SdsNodeId
    MAX-ACCESS  not-accessible
    STATUS      current
    DESCRIPTION
            "Source node ID of the server originating the telemetry value. See
            the sdsNodeInfo table for details. The source node is always all
            zeros for a local telemetry value and set to a valid node ID from
            the sdsNodeInfo table for merged telemetry values."
    ::= { sdsTelemetryEntry 2 }

sdsTelemetryId  OBJECT-TYPE
    SYNTAX      SdsTelemetryId
    MAX-ACCESS  not-accessible
    STATUS      current
    DESCRIPTION
            "Unique ID number of the telemetry value."
    ::= { sdsTelemetryEntry 3 }

sdsTelemetryMerged  OBJECT-TYPE
    SYNTAX      TruthValue
    MAX-ACCESS  read-only
    STATUS      current
    DESCRIPTION
            "Boolean controlling whether the telemetry value is merged or not."
    ::= { sdsTelemetryEntry 4 }

sdsTelemetryRawValue  OBJECT-TYPE
    SYNTAX      Unsigned32
    MAX-ACCESS  read-only
    STATUS      current
    DESCRIPTION
            "Raw unscaled numeric telemetry value."
    ::= { sdsTelemetryEntry 5 }

sdsTelemetryRawAvg  OBJECT-TYPE
    SYNTAX      Unsigned32
    MAX-ACCESS  read-only
    STATUS      current
    DESCRIPTION
            "Raw average numeric telemetry value."
    ::= { sdsTelemetryEntry 6 }

sdsTelemetryUpdateTime  OBJECT-TYPE
    SYNTAX      SdsDateAndTime
    MAX-ACCESS  read-only
    STATUS      current
    DESCRIPTION
            "Timestamp containing the last time that this specific telemetry
            value was updated."
    ::= { sdsTelemetryEntry 7 }

sdsTelemetryThreshInfo  OBJECT-TYPE
    SYNTAX      OCTET STRING
    MAX-ACCESS  read-only
    STATUS      current
    DESCRIPTION
            "Information string showing whether any thresholds are currently
            exceeded."
    ::= { sdsTelemetryEntry 8 }

sdsTelemetrySubId  OBJECT-TYPE
    SYNTAX      Integer32 (0..2147483647)
    MAX-ACCESS  read-only
    STATUS      current
    DESCRIPTION
            "For arrayed telemetry values, this contains the sub ID."
    ::= { sdsTelemetryEntry 9 }

sdsTelemetryName  OBJECT-TYPE
    SYNTAX      SdsTelemetryName
    MAX-ACCESS  read-only
    STATUS      current
    DESCRIPTION
            "Telemetry value name with expanded sub ID."
    ::= { sdsTelemetryEntry 10 }


sdsResynchObjects       OBJECT IDENTIFIER ::= { sdsMIBObjects 5 }

sdsResynchSrcNode OBJECT-TYPE
    SYNTAX      SdsNodeId
    MAX-ACCESS  read-only
    STATUS      current
    DESCRIPTION
            "The notification source node."
    ::= { sdsResynchObjects 1 }

sdsResynchSrcHostname OBJECT-TYPE
    SYNTAX      DisplayString
    MAX-ACCESS  read-only
    STATUS      current
    DESCRIPTION
            "The notification source node's hostname."
    ::= { sdsResynchObjects 2 }

sdsResynchActiveNode OBJECT-TYPE
    SYNTAX      SdsNodeId
    MAX-ACCESS  read-only
    STATUS      current
    DESCRIPTION
            "The notification Active node."
    ::= { sdsResynchObjects 3 }

sdsResynchActiveHostname OBJECT-TYPE
    SYNTAX      DisplayString
    MAX-ACCESS  read-only
    STATUS      current
    DESCRIPTION
            "The notification Active node's hostname."
    ::= { sdsResynchObjects 4 }

sdsResynchManagedObject OBJECT-TYPE
    SYNTAX      OBJECT IDENTIFIER
    MAX-ACCESS  read-only
    STATUS      current
    DESCRIPTION
            "The notification's managed object id."
    ::= { sdsResynchObjects 5 }

sdsResynchAdditionalInfo OBJECT-TYPE
    SYNTAX      DisplayString
    MAX-ACCESS  read-only
    STATUS      current
    DESCRIPTION
            "Comma-separated triplets of key flag, name and value."
    ::= { sdsResynchObjects 6 }


sdsResynchNotifications OBJECT IDENTIFIER ::= { sdsMIB 3 }

sdsToActiveFailover NOTIFICATION-TYPE
    OBJECTS {
        sdsAlarmSequence,
        sdsResynchSrcNode,
        sdsResynchSrcHostname,
        sdsResynchManagedObject,
        sdsResynchAdditionalInfo
    }
    STATUS current
    DESCRIPTION
        "Notifies that HA failover caused the server role change 
        to Active for policy 0"
    ::= { sdsResynchNotifications 1 }

sdsFromActiveFailover NOTIFICATION-TYPE
    OBJECTS {
        sdsAlarmSequence,
        sdsResynchSrcNode,
        sdsResynchSrcHostname,
        sdsResynchActiveNode,
        sdsResynchActiveHostname,
        sdsResynchManagedObject,
        sdsResynchAdditionalInfo
    }
    STATUS current
    DESCRIPTION
        "Notifies that HA failover caused the server role change 
        from Active to a different state for policy 0"
    ::= { sdsResynchNotifications 2 }


tklcNbiResynchRecommended NOTIFICATION-TYPE
    OBJECTS {
        sdsAlarmSequence,
        sdsResynchSrcNode,
        sdsResynchSrcHostname,
        sdsResynchManagedObject,
        sdsResynchAdditionalInfo
    }
    STATUS current
    DESCRIPTION
        "Notifies that resynchronization of alarm table is recommended"
    ::= { sdsResynchNotifications 3 }


sdsMIBNotifications  OBJECT IDENTIFIER ::= { sdsMIB 2 }


sdsSwFaultNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Program impaired by s/w fault"
    ::= { sdsMIBNotifications 31000 }
        

sdsSwStatusNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Program status"
    ::= { sdsMIBNotifications 31001 }
        

sdsProcWatchdogFailureNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Process watchdog timed out"
    ::= { sdsMIBNotifications 31002 }
        

sdsThreadWatchdogFailureNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Thread watchdog timed out"
    ::= { sdsMIBNotifications 31003 }
        

sdsTestStatNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "For testing purposes only"
    ::= { sdsMIBNotifications 31004 }
        

sdsTestFaultNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "For testing purposes only"
    ::= { sdsMIBNotifications 31005 }
        

sdsDbReplicationFaultNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The DB replication process is impaired by a s/w fault"
    ::= { sdsMIBNotifications 31100 }
        

sdsDbRepToSlaveFailureNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "DB replication to a slave DB has failed"
    ::= { sdsMIBNotifications 31101 }
        

sdsDbRepFromMasterFailureNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "DB replication from a master DB has failed"
    ::= { sdsMIBNotifications 31102 }
        

sdsDbRepUpdateFaultNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "DB Replication process cannot apply update to DB"
    ::= { sdsMIBNotifications 31103 }
        

sdsDbRepLatencyNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "DB Replication latency has exceeded thresholds"
    ::= { sdsMIBNotifications 31104 }
        

sdsDbMergeFaultNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The DB merge process (inetmerge) is impaired by a s/w fault"
    ::= { sdsMIBNotifications 31105 }
        

sdsDbMergeToParentFailureNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "DB merging to the parent Merge Node has failed"
    ::= { sdsMIBNotifications 31106 }
        

sdsDbMergeFromChildFailureNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "DB merging from a child Source Node has failed"
    ::= { sdsMIBNotifications 31107 }
        

sdsDbMergeLatencyNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "DB Merge latency has exceeded thresholds"
    ::= { sdsMIBNotifications 31108 }
        

sdsTopErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Topology is configured incorrectly"
    ::= { sdsMIBNotifications 31109 }
        

sdsDbAuditFaultNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The DB audit process (iaudit) is impaired by a s/w fault"
    ::= { sdsMIBNotifications 31110 }
        

sdsDbMergeAuditNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "DB Merge Audit between mate nodes in progress"
    ::= { sdsMIBNotifications 31111 }
        

sdsDbRepUpLogTransTimeoutNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "DB Replicated data may not have transferred in the time allotted."
    ::= { sdsMIBNotifications 31112 }
        

sdsDbReplicationManuallyDisabledNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Replication Manually Disabled"
    ::= { sdsMIBNotifications 31113 }
        

sdsDbReplicationSoapFaultNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "DB Replication of configuration data via SOAP has failed"
    ::= { sdsMIBNotifications 31114 }
        

sdsDbServiceFaultNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The DB service process (idbsvc) is impaired by a s/w fault"
    ::= { sdsMIBNotifications 31115 }
        

sdsExcessiveSharedMemoryConsumptionNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The amount of shared memory consumed exceeds configured thresholds"
    ::= { sdsMIBNotifications 31116 }
        

sdsLowDiskFreeNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The amount of free disk is below configured thresholds"
    ::= { sdsMIBNotifications 31117 }
        

sdsDbDiskStoreFaultNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Writing the database to disk failed"
    ::= { sdsMIBNotifications 31118 }
        

sdsDbUpdateLogOverrunNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The DB update log was overrun increasing risk of data loss"
    ::= { sdsMIBNotifications 31119 }
        

sdsDbUpdateLogWriteFaultNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "A DB change cannot be stored in the updatelog"
    ::= { sdsMIBNotifications 31120 }
        

sdsLowDiskFreeEarlyWarningNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The amount of free disk is below configured early warning thresholds"
    ::= { sdsMIBNotifications 31121 }
        

sdsExcessiveShMemConsumptionEarlyWarnNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The amount of shared memory consumed exceeds configured early warning thresholds"
    ::= { sdsMIBNotifications 31122 }
        

sdsDbRepAuditCmdCompleteNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "ADIC completed successfully"
    ::= { sdsMIBNotifications 31123 }
        

sdsDbRepAuditCmdErrNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "An ADIC detected errors"
    ::= { sdsMIBNotifications 31124 }
        

sdsDbDurabilityDegradedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "DB durability has dropped below configured durability level"
    ::= { sdsMIBNotifications 31125 }
        

sdsAuditBlockedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Site Audit Controls blocked an inter-site replication audit due to the number in progress per configuration"
    ::= { sdsMIBNotifications 31126 }
        

sdsDbRepAuditCompleteNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "DB replication audit completed"
    ::= { sdsMIBNotifications 31127 }
        

sdsDbADICErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "ADIC found one or more errors that are not automatically fixable."
    ::= { sdsMIBNotifications 31128 }
        

sdsDbADICWarnNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "ADIC found one or more minor issues that can most likely be ignored."
    ::= { sdsMIBNotifications 31129 }
        

sdsNetworkHealthWarningNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Network health issue detected."
    ::= { sdsMIBNotifications 31130 }
        

sdsOustedThrottleWarnNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "DB ousted throttle may be affecting processes."
    ::= { sdsMIBNotifications 31131 }
        

sdsDbRepPrecRelaxedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Standby Database updates are falling behind.  Relaxing the replication barrier to allow non-Standby Databases to update as fast as possible."
    ::= { sdsMIBNotifications 31132 }
        

sdsDbRepSwitchoverNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "DB Replication Active to Standby switchover exceeded maximum swithover time."
    ::= { sdsMIBNotifications 31133 }
        

sdsDbSiteRepToSlaveFailureNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "DB Site replication to a slave DB has failed"
    ::= { sdsMIBNotifications 31134 }
        

sdsDbSiteRepFromMasterFailureNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "DB Site replication from a master DB has failed"
    ::= { sdsMIBNotifications 31135 }
        

sdsDbSiteRepPrecRelaxedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Standby Site Database updates are falling behind.  Relaxing the replication barrier to allow non-Standby Site Databases to update as fast as possible."
    ::= { sdsMIBNotifications 31136 }
        

sdsDbSiteRepLatencyNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "DB Site Replication latency has exceeded thresholds"
    ::= { sdsMIBNotifications 31137 }
        

sdsDbPerlFaultNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Perl interface to DB is impaired by a s/w fault"
    ::= { sdsMIBNotifications 31140 }
        

sdsDbSQLFaultNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "SQL interface to DB is impaired by a s/w fault"
    ::= { sdsMIBNotifications 31145 }
        

sdsDbMastershipFaultNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "DB replication is impaired due to no mastering process (inetrep)"
    ::= { sdsMIBNotifications 31146 }
        

sdsDbUpSyncLogOverrunNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "UpSyncLog is not big enough for (WAN) replication"
    ::= { sdsMIBNotifications 31147 }
        

sdsDbLockErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "DB lock integrity error detected"
    ::= { sdsMIBNotifications 31148 }
        

sdsDbLateWriteNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Application wrote to database while HA role change from active was in progress"
    ::= { sdsMIBNotifications 31149 }
        

sdsDbHealthImpactNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Database health impacted"
    ::= { sdsMIBNotifications 31150 }
        

sdsDbHealthImpactPersistNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Persistent database failure "
    ::= { sdsMIBNotifications 31151 }
        

sdsProcMgmtFaultNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The process manager (procmgr) is impaired by a s/w fault"
    ::= { sdsMIBNotifications 31200 }
        

sdsProcNotRunningNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "A managed process cannot be started or has unexpectedly terminated"
    ::= { sdsMIBNotifications 31201 }
        

sdsProcZombieProcessNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "A zombie process exists that cannot be killed by procmgr.  procmgr will no longer manage this process.  If the process does not exit, it may be necessary to reboot the server to eliminate the zombie process."
    ::= { sdsMIBNotifications 31202 }
        

sdsProcMgmtMonFaultNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The process manager monitor (pm.watchdog) is impaired by a s/w fault"
    ::= { sdsMIBNotifications 31206 }
        

sdsProcResourceMonFaultNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The process resource monitor (ProcWatch) is impaired by a s/w fault"
    ::= { sdsMIBNotifications 31207 }
        

sdsPortServerFaultNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The run environment port mapper (re.portmap) is impaired by a s/w fault"
    ::= { sdsMIBNotifications 31208 }
        

sdsHostLookupFailedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Unable to resolve a hostname specified in the NodeInfo table."
    ::= { sdsMIBNotifications 31209 }
        

sdsProcSchedulerFaultNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The process scheduler (ProcSched/runat) is impaired by a s/w fault"
    ::= { sdsMIBNotifications 31213 }
        

sdsScheduleProcessFaultNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "A scheduled process cannot be executed or abnormally terminated"
    ::= { sdsMIBNotifications 31214 }
        

sdsProcResourcesExceededFaultNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "A process is consuming excessive system resources"
    ::= { sdsMIBNotifications 31215 }
        

sdsSysMetricConfigErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "A SysMetric configuration table contains invalid data"
    ::= { sdsMIBNotifications 31216 }
        

sdsNetworkUnreachableWarningNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Unreachable Network Detected"
    ::= { sdsMIBNotifications 31217 }
        

sdsHaCfgMonitorFaultNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  obsolete
    DESCRIPTION
            "The HA manager (cmha) is impaired by a s/w fault"
    ::= { sdsMIBNotifications 31220 }
        

sdsHaAlarmMonitorFaultNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  obsolete
    DESCRIPTION
            "The high availability alarm monitor is impaired by a s/w fault"
    ::= { sdsMIBNotifications 31221 }
        

sdsHaNotConfiguredNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  obsolete
    DESCRIPTION
            "High availability is disabled due to system configuration"
    ::= { sdsMIBNotifications 31222 }
        

sdsHaHbTransmitFailureNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  obsolete
    DESCRIPTION
            "The high availability monitor failed to send heartbeat"
    ::= { sdsMIBNotifications 31223 }
        

sdsHaCfgErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "High availability configuration error"
    ::= { sdsMIBNotifications 31224 }
        

sdsHaSvcStartFailureNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The required high availability resource failed to start"
    ::= { sdsMIBNotifications 31225 }
        

sdsHaAvailDegradedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The high availability status is degraded due to raised alarms"
    ::= { sdsMIBNotifications 31226 }
        

sdsHaAvailFailedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The high availability status is failed due to raised alarms"
    ::= { sdsMIBNotifications 31227 }
        

sdsHaStandbyOfflineNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  obsolete
    DESCRIPTION
            "HA Standby Server Offline"
    ::= { sdsMIBNotifications 31228 }
        

sdsHaScoreChangeNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "High availability health score changed"
    ::= { sdsMIBNotifications 31229 }
        

sdsHaLateHeartbeatWarningNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "High availability server has not received a message on specified path within the configured interval"
    ::= { sdsMIBNotifications 31232 }
        

sdsHaPathDownNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "High availability path loss of connectivity"
    ::= { sdsMIBNotifications 31233 }
        

sdsHaLinkDownNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "High availability TCP link is down"
    ::= { sdsMIBNotifications 31236 }
        

sdsRecAlarmEvProcFaultNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The recent alarm event manager (raclerk) is impaired by a s/w fault"
    ::= { sdsMIBNotifications 31230 }
        

sdsPlatAlarmAgentNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The platform alarm agent impaired by a s/w fault"
    ::= { sdsMIBNotifications 31231 }
        

sdsUtrustedTimeOnInitNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Upon system initialization, the system time is not trusted probably because NTP is misconfigured or the NTP servers are unreachable.  There are often accompanying Platform alarms to guide correction.  Generally, applications are not started if time is not believed to be correct on start-up. Recovery will often will require rebooting the server."
    ::= { sdsMIBNotifications 31234 }
        

sdsUtrustedTimePostInitNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "After system initialization, the system time has become untrusted probably because NTP has reconfigured improperly, time has been manually changed, the NTP servers are unreachable, etc.  There are often accompanying Platform alarms to guide correction.  Generally, applications remaining be running, but time-stamped data is likely incorrect, reports may be negatively affected, some behavior may be improper, etc."
    ::= { sdsMIBNotifications 31235 }
        

sdsMeasCollectorFaultNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The measurements collector (statclerk) is impaired by a s/w fault"
    ::= { sdsMIBNotifications 31240 }
        

sdsRePortMappingFaultNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The IP service port mapper (re.portmap) is impaired by a s/w fault"
    ::= { sdsMIBNotifications 31250 }
        

sdsSnmpAgentNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The SNMP agent (cmsnmpa) is impaired by a s/w fault"
    ::= { sdsMIBNotifications 31260 }
        

sdsSnmpConfigNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "A SNMP configuration error was detected"
    ::= { sdsMIBNotifications 31261 }
        

sdsLoggingOutputNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Logging Output set to Above Normal"
    ::= { sdsMIBNotifications 31270 }
        

sdsActiveToStandbyTransNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  obsolete
    DESCRIPTION
            "HA active to standby activity transition"
    ::= { sdsMIBNotifications 31280 }
        

sdsStandbyToActiveTransNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  obsolete
    DESCRIPTION
            "HA standby to active activity transition"
    ::= { sdsMIBNotifications 31281 }
        

sdsHaMgmtFaultNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The HA manager (cmha) is impaired by a s/w fault"
    ::= { sdsMIBNotifications 31282 }
        

sdsHaServerOfflineNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "High availability server is offline"
    ::= { sdsMIBNotifications 31283 }
        

sdsHaRemoteHeartbeatWarningNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "High availability remote subscriber has not received a heartbeat within the configured interval"
    ::= { sdsMIBNotifications 31284 }
        

sdsHaSbrEntryNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "High availability node join recovery entered "
    ::= { sdsMIBNotifications 31285 }
        

sdsHaSbrPlanNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "High availability node join recovery plan "
    ::= { sdsMIBNotifications 31286 }
        

sdsHaSbrCompleteNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "High availability node join recovery complete "
    ::= { sdsMIBNotifications 31287 }
        

sdsHaBadSiteCfgNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "High availability site configuration error"
    ::= { sdsMIBNotifications 31288 }
        


sdsHaProcessStatusNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "HA manager (cmha) status"
    ::= { sdsMIBNotifications 31290 }
        

sdsHaElectionStatusNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "HA DC Election status"
    ::= { sdsMIBNotifications 31291 }
        

sdsHaPolicyStatusNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "HA Policy plan status"
    ::= { sdsMIBNotifications 31292 }
        

sdsHaRaLinkStatusNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "HA Resource Agent Link status"
    ::= { sdsMIBNotifications 31293 }
        

sdsHaResourceStatusNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "HA Resource registration status"
    ::= { sdsMIBNotifications 31294 }
        

sdsHaActionStatusNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "HA Resource action status"
    ::= { sdsMIBNotifications 31295 }
        

sdsHaMonitorStatusNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "HA Monitor action status"
    ::= { sdsMIBNotifications 31296 }
        

sdsHaRaInfoNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "HA Resource Agent application information"
    ::= { sdsMIBNotifications 31297 }
        

sdsHaRaDetailNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "HA Resource Agent application detailed information"
    ::= { sdsMIBNotifications 31298 }
        

sdsHaNotificationNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "HA Notification status"
    ::= { sdsMIBNotifications 31299 }
        

sdsHaControlNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "HA Control action status"
    ::= { sdsMIBNotifications 31300 }
        

sdsHaTopologyNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "HA Topology Events"
    ::= { sdsMIBNotifications 31301 }
        

sdsHaBadCfgNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "High availability configuration error"
    ::= { sdsMIBNotifications 31322 }
        

sdsTpdBrkPnlFeedUnavailableNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Breaker Panel Feed Unavailable"
    ::= { sdsMIBNotifications 32100 }


sdsTpdBrkPnlBreakerFailureNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Breaker Panel Breaker Failure"
    ::= { sdsMIBNotifications 32101 }


sdsTpdBrkPnlMntFailureNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Breaker Panel Monitoring Failure"
    ::= { sdsMIBNotifications 32102 }


sdsTpdPowerFeedUnavailNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Power Feed Unavailable"
    ::= { sdsMIBNotifications 32103 }


sdsTpdPowerSupply1FailureNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  deprecated
    DESCRIPTION
            "Power Supply 1 Failure - deprecated"
    ::= { sdsMIBNotifications 32104 }


sdsTpdPowerSupply2FailureNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  deprecated
    DESCRIPTION
            "Power Supply 2 Failure - deprecated"
    ::= { sdsMIBNotifications 32105 }


sdsTpdPowerSupply3FailureNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  deprecated
    DESCRIPTION
            "Power Supply 3 Failure - deprecated"
    ::= { sdsMIBNotifications 32106 }


sdsTpdRaidFeedUnavailableNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "RAID Feed Unavailable"
    ::= { sdsMIBNotifications 32107 }


sdsTpdRaidPower1FailureNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "RAID Power Supply 1 Failure"
    ::= { sdsMIBNotifications 32108 }


sdsTpdRaidPower2FailureNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "RAID Power Supply 2 Failure"
    ::= { sdsMIBNotifications 32109 }


sdsTpdRaidPower3FailureNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "RAID Power Supply 3 Failure"
    ::= { sdsMIBNotifications 32110 }


sdsTpdDeviceFailureNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Device Failure"
    ::= { sdsMIBNotifications 32111 }


sdsTpdDeviceIfFailureNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Device Interface Failure"
    ::= { sdsMIBNotifications 32112 }


sdsTpdEccUncorrectableErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Uncorrectable ECC Memory Error"
    ::= { sdsMIBNotifications 32113 }


sdsTpdSNMPGetFailureNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "SNMP Get Failure"
    ::= { sdsMIBNotifications 32114 }


sdsTpdChronyDaemonNotSynchronizedFailureNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Chrony Daemon Lost Synchronization For Extended Time"
    ::= { sdsMIBNotifications 32115 }


sdsTpdNTPTimeGoneBackwardsNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server's Time Has Gone Backwards"
    ::= { sdsMIBNotifications 32116 }


sdsNtpOffsetCheckFailureNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "NTP Offset Check Failure"
    ::= { sdsMIBNotifications 32117 }


sdsTpdFanErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Fan Failure. This test uses the leaky bucket algorithm."
    ::= { sdsMIBNotifications 32300 }


sdsTpdIntDiskErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Internal Disk Error"
    ::= { sdsMIBNotifications 32301 }


sdsTpdRaidDiskErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server RAID Disk Error"
    ::= { sdsMIBNotifications 32302 }


sdsTpdPlatformErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Platform Error"
    ::= { sdsMIBNotifications 32303 }


sdsTpdFileSystemErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server File System Error"
    ::= { sdsMIBNotifications 32304 }


sdsTpdPlatProcessErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Platform Process Error"
    ::= { sdsMIBNotifications 32305 }


sdsTpdRamShortageErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server RAM Shortage Error. This test uses the leaky bucket algorithm."
    ::= { sdsMIBNotifications 32306 }


sdsTpdSwapSpaceShortageErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Swap Space Shortage Error. This test uses the leaky bucket algorithm."
    ::= { sdsMIBNotifications 32307 }


sdsTpdProvNetworkErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Provisioning Network Error"
    ::= { sdsMIBNotifications 32308 }


sdsTpdEagleNetworkAErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Eagle Network A Error"
    ::= { sdsMIBNotifications 32309 }


sdsTpdEagleNetworkBErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Eagle Network B Error"
    ::= { sdsMIBNotifications 32310 }


sdsTpdSyncNetworkErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Sync Network Error"
    ::= { sdsMIBNotifications 32311 }


sdsTpdDiskSpaceShortageErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Disk Space Shortage Error"
    ::= { sdsMIBNotifications 32312 }


sdsTpdDefaultRouteNetworkErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Default Route Network Error"
    ::= { sdsMIBNotifications 32313 }


sdsTpdTemperatureErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Temperature Error"
    ::= { sdsMIBNotifications 32314 }


sdsTpdMainboardVoltageErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Mainboard Voltage Error"
    ::= { sdsMIBNotifications 32315 }


sdsTpdPowerFeedErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Power Feed Error"
    ::= { sdsMIBNotifications 32316 }


sdsTpdDiskHealthErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Disk Health Test Error"
    ::= { sdsMIBNotifications 32317 }


sdsTpdDiskUnavailableErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Disk Unavailable Error"
    ::= { sdsMIBNotifications 32318 }


sdsTpdDeviceErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Device Error"
    ::= { sdsMIBNotifications 32319 }


sdsTpdDeviceIfErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Device Interface Error"
    ::= { sdsMIBNotifications 32320 }


sdsTpdEccCorrectableErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Correctable ECC Memory Error"
    ::= { sdsMIBNotifications 32321 }


sdsTpdPowerSupply1ErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Power Supply A Error"
    ::= { sdsMIBNotifications 32322 }


sdsTpdPowerSupply2ErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Power Supply B Error"
    ::= { sdsMIBNotifications 32323 }


sdsTpdBrkPnlFeedErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Breaker Panel Feed Error"
    ::= { sdsMIBNotifications 32324 }


sdsTpdBrkPnlBreakerErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Breaker Panel Breaker Error"
    ::= { sdsMIBNotifications 32325 }


sdsTpdBrkPnlMntErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Breaker Panel Monitoring Error"
    ::= { sdsMIBNotifications 32326 }


sdsTpdHaKeepaliveErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server HA Keepalive Error"
    ::= { sdsMIBNotifications 32327 }


sdsTpdDrbdUnavailableNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "DRBD block device can not be mounted."
    ::= { sdsMIBNotifications 32328 }


sdsTpdDrbdNotReplicatingNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "DRBD block device is not being replicated to peer."
    ::= { sdsMIBNotifications 32329 }


sdsTpdDrbdPeerProblemNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "DRBD peer needs intervention."
    ::= { sdsMIBNotifications 32330 }


sdsTpdHpDiskProblemNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "HP Disks need intervention."
    ::= { sdsMIBNotifications 32331 }


sdsTpdHpDiskCtrlrProblemNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "HP Smart Array controller needs intervention."
    ::= { sdsMIBNotifications 32332 }


sdsTpdHPACUCLIProblemNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The hpacucliStatus utility needs intervention."
    ::= { sdsMIBNotifications 32333 }


sdsTpdMpathDeviceProblemNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Multipath device access link needs intervention."
    ::= { sdsMIBNotifications 32334 }


sdsTpdSwitchLinkDownErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Switch Link Down Error"
    ::= { sdsMIBNotifications 32335 }


sdsTpdHalfOpenSockLimitNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Half open TCP sockets limit reached"
    ::= { sdsMIBNotifications 32336 }


sdsTpdFlashProgramFailureNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Flash device failed to update"
    ::= { sdsMIBNotifications 32337 }


sdsTpdSerialMezzUnseatedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Serial Mezzanine card is not seated properly"
    ::= { sdsMIBNotifications 32338 }


sdsTpdMaxPidLimitNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Max number running of proccesss limit reached"
    ::= { sdsMIBNotifications 32339 }


sdsTpdChronyDaemonNotSynchronizedErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Chrony Daemon Lost Synchronization For Extended Time"
    ::= { sdsMIBNotifications 32340 }


sdsTpdChronyDaemonNeverSynchronizedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Chrony Daemon Never Synchronized"
    ::= { sdsMIBNotifications 32341 }


sdsNtpOffsetCheckErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "NTP Offset Check Failure"
    ::= { sdsMIBNotifications 32342 }


sdsTpdDiskProblemNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "RAID disk member(s) need intervention."
    ::= { sdsMIBNotifications 32343 }


sdsTpdDiskCtrlrProblemNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "RAID controller needs intervention."
    ::= { sdsMIBNotifications 32344 }


sdsTpdUpgradeSnapshotInvalidNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "LVM snapshot is invalid"
    ::= { sdsMIBNotifications 32345 }


sdsTpdOEMHardwareProblemNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "OEM hardware management service reports an error"
    ::= { sdsMIBNotifications 32346 }


sdsTpdHWMGMTCLIProblemNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The hwmgmtcliStatus daemon needs intervention"
    ::= { sdsMIBNotifications 32347 }


sdsTpdFipsSubsystemProblemNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The FIPS subsystem needs intervention"
    ::= { sdsMIBNotifications 32348 }


sdsTpdHidsFileTamperingNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "HIDS has detected file tampering"
    ::= { sdsMIBNotifications 32349 }


sdsTpdSecurityProcessDownNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "HIDS detected security process is down"
    ::= { sdsMIBNotifications 32350 }


sdsTpdDiskSpaceShortageWarningNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Disk Space Shortage Warning"
    ::= { sdsMIBNotifications 32500 }


sdsTpdApplicationProcessErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Application Process Error"
    ::= { sdsMIBNotifications 32501 }


sdsTpdHardwareConfigErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Hardware Configuration Error"
    ::= { sdsMIBNotifications 32502 }


sdsTpdRamShortageWarningNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server RAM Shortage Warning. This test uses the leaky bucket algorithm."
    ::= { sdsMIBNotifications 32503 }


sdsTpdSoftwareConfigErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Software Configuration Error"
    ::= { sdsMIBNotifications 32504 }


sdsTpdSwapSpaceShortageWarningNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Swap Space Shortage Warning. This test uses the leaky bucket algorithm."
    ::= { sdsMIBNotifications 32505 }


sdsTpdDefaultRouteNotDefinedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Default Router not Defined"
    ::= { sdsMIBNotifications 32506 }


sdsTpdTemperatureWarningNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Temperature Warning"
    ::= { sdsMIBNotifications 32507 }


sdsTpdCoreFileDetectedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Core File Detected"
    ::= { sdsMIBNotifications 32508 }


sdsTpdChronyDaemonNotSynchronizedWarningNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Chrony Daemon Not Synchronized"
    ::= { sdsMIBNotifications 32509 }


sdsTpdCMOSBatteryVoltageLowNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "CMOS Battery Voltage Low"
    ::= { sdsMIBNotifications 32510 }


sdsTpdSmartTestWarnNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Disk Self Test Warning"
    ::= { sdsMIBNotifications 32511 }


sdsTpdDeviceWarnNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Device Warning"
    ::= { sdsMIBNotifications 32512 }


sdsTpdDeviceIfWarnNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Device Interface Warning"
    ::= { sdsMIBNotifications 32513 }


sdsTpdWatchdogRebootNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Reboot Watchdog Initiated"
    ::= { sdsMIBNotifications 32514 }


sdsTpdHaInhibitedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server HA Failover Inhibited"
    ::= { sdsMIBNotifications 32515 }


sdsTpdHaActiveToStandbyTransNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server HA Active To Standby Transition"
    ::= { sdsMIBNotifications 32516 }


sdsTpdHaStandbyToActiveTransNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server HA Standby To Active Transition"
    ::= { sdsMIBNotifications 32517 }


sdsTpdPlatformHealthCheckFailedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Platform Health Check Failure"
    ::= { sdsMIBNotifications 32518 }


sdsNtpOffsetCheckFailedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "NTP Offset Check Failure"
    ::= { sdsMIBNotifications 32519 }


sdsNtpStratumCheckFailedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "NTP Stratum Check Failure"
    ::= { sdsMIBNotifications 32520 }


sdsSasPresenceSensorMissingNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "SAS Presence Sensor Missing"
    ::= { sdsMIBNotifications 32521 }


sdsSasDriveMissingNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "SAS Drive Missing"
    ::= { sdsMIBNotifications 32522 }


sdsTpdDrbdFailoverBusyNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "This DRBD node is not currently ready to act as primary."
    ::= { sdsMIBNotifications 32523 }


sdsTpdHpDiskResyncNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "HP Disk is resyncing."
    ::= { sdsMIBNotifications 32524 }


sdsTpdTelcoFanWarningNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Telco Fan Warning"
    ::= { sdsMIBNotifications 32525 }


sdsTpdTelcoTemperatureWarningNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Telco Temperature Warning"
    ::= { sdsMIBNotifications 32526 }


sdsTpdTelcoPowerSupplyWarningNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Telco Power Supply Warning"
    ::= { sdsMIBNotifications 32527 }


sdsTpdInvalidBiosValueNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Invalid BIOS value"
    ::= { sdsMIBNotifications 32528 }


sdsTpdServerKernelDumpFileDetectedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Kernel Dump File Detected"
    ::= { sdsMIBNotifications 32529 }


sdsTpdServerUpgradeFailDetectedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Upgrade Fail Detected"
    ::= { sdsMIBNotifications 32530 }


sdsTpdHalfOpenSocketWarningNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Half Open TCP Sockets Warning"
    ::= { sdsMIBNotifications 32531 }


sdsTpdServerUpgradePendingAcceptNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Upgrade Pending Accept/Reject"
    ::= { sdsMIBNotifications 32532 }


sdsTpdMaxPidWarningNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Max number running of proccesss limit warning"
    ::= { sdsMIBNotifications 32533 }


sdsTpdNTPSourceIsBadNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "NTP Source Server Is Not Able To Provide Correct Time"
    ::= { sdsMIBNotifications 32534 }


sdsTpdDiskResyncNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "RAID member disk is resyncing."
    ::= { sdsMIBNotifications 32535 }


sdsTpdUpgradeSnapshotWarningNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "LVM snapshot space usage warning"
    ::= { sdsMIBNotifications 32536 }


sdsTpdFipsSubsystemWarningNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The FIPS subsystem needs intervention"
    ::= { sdsMIBNotifications 32537 }


sdsTpdPdcErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Platform Data Collection Error"
    ::= { sdsMIBNotifications 32538 }


sdsTpdServerPatchPendingAcceptNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Patch Pending Accept/Reject"
    ::= { sdsMIBNotifications 32539 }


sdsTpdCpuPowerLimitMismatchNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The BIOS setting for CPU Power Limit is different than expected"
    ::= { sdsMIBNotifications 32540 }


sdsTpdTelcoSwitchNotificationNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Telco Switch Notification"
    ::= { sdsMIBNotifications 32700 }


sdsTpdHidsBaselineCreatedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The TPD HIDS baseline was created"
    ::= { sdsMIBNotifications 32701 }


sdsTpdHidsBaselineDeletedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The TPD HIDS baseline was deleted"
    ::= { sdsMIBNotifications 32702 }


sdsTpdHidsEnabledNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "TPD HIDS has been enabled"
    ::= { sdsMIBNotifications 32703 }


sdsTpdHidsDisabledNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "TPD HIDS has been disabled"
    ::= { sdsMIBNotifications 32704 }


sdsTpdHidsSuspendedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "TPD HIDS monitoring has been suspended"
    ::= { sdsMIBNotifications 32705 }


sdsTpdHidsResumedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "TPD HIDS monitoring has been resumed"
    ::= { sdsMIBNotifications 32706 }


sdsTpdHidsBaselineUpdatedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "TPD HIDS baseline has been updated"
    ::= { sdsMIBNotifications 32707 }






sdsBackupStartNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Backup started"
    ::= { sdsMIBNotifications 10001 }
        

sdsBackupCompleteNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Backup completed"
    ::= { sdsMIBNotifications 10002 }
        

sdsBackupFailNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Backup failed"
    ::= { sdsMIBNotifications 10003 }
        

sdsRestoreStartNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Restoration started"
    ::= { sdsMIBNotifications 10004 }
        

sdsRestoreCompleteNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Restoration completed"
    ::= { sdsMIBNotifications 10005 }
        

sdsRestoreFailNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Restoration failed"
    ::= { sdsMIBNotifications 10006 }
        

sdsProvisioningManuallyDisabled NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Provisioning Manually Disabled"
    ::= { sdsMIBNotifications 10008 }
        

sdsCfgProvDbNoSync NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Config and Prov DB not yet synchronized"
    ::= { sdsMIBNotifications 10009 }
        

sdsStDbNoSync NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Stateful database not yet synchronized with mate database"
    ::= { sdsMIBNotifications 10010 }
        

sdsCantMonitorTable NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Monitoring for table cannot be set up"
    ::= { sdsMIBNotifications 10011 }
        

sdsResponderFailed NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The responder for a monitored table failed to respond to a table change"
    ::= { sdsMIBNotifications 10012 }
        

sdsApplSWDisabled NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Application restart in progress - see additional info (Alarms & Events -> View History) for reason"
    ::= { sdsMIBNotifications 10013 }
        

sdsResourceAuditFailure NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "An unexpected error occured in the execution of an external resource audit"
    ::= { sdsMIBNotifications 10050 }
        

sdsRouteDeploymentFailed NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "An error occured in the deployment of a network route"
    ::= { sdsMIBNotifications 10051 }
        

sdsRouteDiscoveryFailed NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "An error occured in the discovery of network routes"
    ::= { sdsMIBNotifications 10052 }
        

sdsNoRouteDevice NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Could not identify a suitable device for the deployment of a network route"
    ::= { sdsMIBNotifications 10053 }
        

sdsDeviceDeploymentFailed NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "An error occured in the deployment of a network device"
    ::= { sdsMIBNotifications 10054 }
        

sdsDeviceDiscoveryFailed NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "An error occured in the discovery of network devices"
    ::= { sdsMIBNotifications 10055 }
        

sdsSgMaxAllowedHARoleWarn NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server Group Max Allowed HA Role Warning"
    ::= { sdsMIBNotifications 10073 }
        

sdsSbyRecoveryInProgress NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Standby server temporarily degraded while the new active server stabilizes following switch of activity"
    ::= { sdsMIBNotifications 10074 }
        

sdsRecoveryWithoutAppRestart NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The Applications on the Standby server have not been restarted after an active to standby transition since h_FailureCleanupMode is set to 0"
    ::= { sdsMIBNotifications 10078 }
        

sdsIncompatibleDatabaseVersionNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The database version is incompatible with the installed software database version"
    ::= { sdsMIBNotifications 10000 }
        

sdsMtceStopApplications NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The server is no longer providing services because application processes have been manually stopped"
    ::= { sdsMIBNotifications 10075 }
        

sdsLogExportStart NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Log files export operation started"
    ::= { sdsMIBNotifications 10100 }
        

sdsLogExportSuccess NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Log files export operation completed successfully"
    ::= { sdsMIBNotifications 10101 }
        

sdsLogExportFailed NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Log files export operation Failed"
    ::= { sdsMIBNotifications 10102 }
        

sdsLogExportNotRun NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Log files export operation not run - export can only run on Active Network OAMP server"
    ::= { sdsMIBNotifications 10103 }
        

sdsExportXferFailed NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Performance data export remote copy operation Failed"
    ::= { sdsMIBNotifications 10104 }
        

sdsLogExportCancelledUser NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Log files export operation cancelled by user"
    ::= { sdsMIBNotifications 10105 }
        

sdsLogExportCancelledDuplicate NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Log files export operation cancelled - scheduled export already queued"
    ::= { sdsMIBNotifications 10106 }
        

sdsLogExportCancelledQueue NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Log files export operation cancelled - export queue is full"
    ::= { sdsMIBNotifications 10107 }
        

sdsLogExportDupSchedTask NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Duplicate scheduled export task queued"
    ::= { sdsMIBNotifications 10108 }
        

sdsLogExportQueueFull NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Export queue is full"
    ::= { sdsMIBNotifications 10109 }
        

certificateAboutToExpire NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Certificate about to expire"
    ::= { sdsMIBNotifications 10110 }
        

certificateExpired NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Certificate expired"
    ::= { sdsMIBNotifications 10111 }
        

certificateCannotBeUsed NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Certificate cannot be used"
    ::= { sdsMIBNotifications 10112 }
        

sdsLogHealthCheckStart NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Upgrade health check operation started"
    ::= { sdsMIBNotifications 10115 }
        

sdsLogHealthCheckSuccess NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Upgrade health check operation completed successfully"
    ::= { sdsMIBNotifications 10116 }
        

sdsLogHealthCheckFailed NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Upgrade health check operation Failed"
    ::= { sdsMIBNotifications 10117 }
        

sdsLogHealthCheckNotRun NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Upgrade health check operation not run"
    ::= { sdsMIBNotifications 10118 }
        

sdsLogSgUpgradeStart NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server group upgrade operation started"
    ::= { sdsMIBNotifications 10120 }
        

sdsLogSgUpgradeCancelled NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server group upgrade cancelled - validation failed"
    ::= { sdsMIBNotifications 10121 }
        

sdsLogSgUpgradeSuccess NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server group upgrade operation completed successfully"
    ::= { sdsMIBNotifications 10122 }
        

sdsLogSgUpgradeFailed NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server group upgrade operation failed"
    ::= { sdsMIBNotifications 10123 }
        

sdsLogSgUpgradeCancelledUser NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server group upgrade cancelled by user"
    ::= { sdsMIBNotifications 10124 }
        

sdsLogSgUpgradeFailAlm NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server group upgrade operation failed"
    ::= { sdsMIBNotifications 10125 }
        

sdsLogServerUpgradeStart NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server upgrade operation started"
    ::= { sdsMIBNotifications 10130 }
        

sdsLogServerUpgradeCancelled NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server upgrade cancelled - validation failed"
    ::= { sdsMIBNotifications 10131 }
        

sdsLogServerUpgradeSuccess NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server upgrade operation completed successfully"
    ::= { sdsMIBNotifications 10132 }
        

sdsLogServerUpgradeFailed NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server upgrade operation failed"
    ::= { sdsMIBNotifications 10133 }
        

sdsLogServerUpgradeFailAlm NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Server upgrade operation failed"
    ::= { sdsMIBNotifications 10134 }
        

sdsLogSiteUpgradeStart NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Site upgrade operation started"
    ::= { sdsMIBNotifications 10140 }
        

sdsLogSiteUpgradeCancelled NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Site upgrade cancelled - validation failed"
    ::= { sdsMIBNotifications 10141 }
        

sdsLogSiteUpgradeSuccess NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Site upgrade operation completed successfully"
    ::= { sdsMIBNotifications 10142 }
        

sdsLogSiteUpgradeFailed NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Site upgrade operation failed"
    ::= { sdsMIBNotifications 10143 }
        

sdsLogSiteUpgradeCancelledUser NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Site upgrade cancelled by user"
    ::= { sdsMIBNotifications 10144 }
        

sdsLogSiteUpgradeFailAlm NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Site upgrade operation failed"
    ::= { sdsMIBNotifications 10145 }
        

sdsLoginSuccess NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Login Successful"
    ::= { sdsMIBNotifications 10151 }
        

sdsLoginFailed NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Login Failed"
    ::= { sdsMIBNotifications 10152 }
        

sdsLogoutSuccess NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Logout Successful"
    ::= { sdsMIBNotifications 10153 }
        

sdsAccountDisabled NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "User Account disabled due to multiple login failures"
    ::= { sdsMIBNotifications 10154 }
        

sdsSamlLoginSuccess NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "SAML Login Successful"
    ::= { sdsMIBNotifications 10155 }
        

sdsSamlLoginFailed NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "SAML Login Failed"
    ::= { sdsMIBNotifications 10156 }
        

sdsSgDbReinit NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Remote Database re-initialization in progress"
    ::= { sdsMIBNotifications 10200 }
        

sdsBackupFailure NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Database backup failed"
    ::= { sdsMIBNotifications 10020 }
        

sdsSnmpTrappingNotConfiguredForSite NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "SNMP Trapping Not Configured for Site"
    ::= { sdsMIBNotifications 10300 }
        




sdsProcessCpuUtilizationNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The Process, which is responsible for handling all traffic, is approaching or exceeding its engineered traffic handling capacity."
    ::= { sdsMIBNotifications 19900 }
        

sdsCfgDbValidationErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "A minor database validation error was detected on the MP server during an update. MP internal database is now out of sync with the configuration database. Subsequent database operations on the MP are ALLOWED."
    ::= { sdsMIBNotifications 19901 }
        

sdsCfgDbUpdateFailureNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "A critical database validation error was detected on the MP server during an update. MP internal database is now out of sync with the configuration database. Subsequent database operations on the MP are DISABLED."
    ::= { sdsMIBNotifications 19902 }
        

sdsCfgDbPostUpdateErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "A minor database validation error was detected on the MP server after a database update. MP internal database is still in sync with the configuration database. Subsequent database operations on the MP are ALLOWED."
    ::= { sdsMIBNotifications 19903 }
        

sdsCfgDbPostFailureNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "A critical database validation error was detected on the MP server after a database update. MP internal database is still in sync with the configuration database. Subsequent database operations on the MP are DISABLED."
    ::= { sdsMIBNotifications 19904 }
        

sdsMeasurementInitializationFailureNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "A measurement object failed to initialize."
    ::= { sdsMIBNotifications 19905 }
        






sdsEventEgressMessageDiscardedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Egress Message Discarded"
    ::= { sdsMIBNotifications 19810 }
        

sdsEventIngressMessageDiscardedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Ingress Message Discarded"
    ::= { sdsMIBNotifications 19811 }
        

sdsEventHeartbeatMissedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Peer has not responded to heartbeat."
    ::= { sdsMIBNotifications 19814 }
        

sdsEventConnectionStateChangeNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Connection state Changed"
    ::= { sdsMIBNotifications 19816 }
        

sdsEventComAgtConfigParamChangeNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent DB Responder detected a change in configurable control option parameter"
    ::= { sdsMIBNotifications 19817 }
        

sdsEventComAgtSvcRegChangedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Service Registration State Change"
    ::= { sdsMIBNotifications 19830 }
        

sdsEventComAgtSvcOpStateChangedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Service Operational State Changed"
    ::= { sdsMIBNotifications 19831 }
        

sdsEventComAgtTransFailedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Reliable Transaction Failed"
    ::= { sdsMIBNotifications 19832 }
        

sdsEventRoutingFailedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Service Egress Message Discarded"
    ::= { sdsMIBNotifications 19833 }
        

sdsEventResourceProviderRegisteredNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Resource-Provider Registered"
    ::= { sdsMIBNotifications 19842 }
        

sdsEventResourceStateChangeNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Resource-Provider Resource State Changed"
    ::= { sdsMIBNotifications 19843 }
        

sdsEventStaleHBPacketNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Resource-Provider Stale Status Received"
    ::= { sdsMIBNotifications 19844 }
        

sdsEventResourceProviderDeRegisteredNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Resource-Provider Deregistered"
    ::= { sdsMIBNotifications 19845 }
        

sdsEventResourceUserRegisteredNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Resource-USer Registered"
    ::= { sdsMIBNotifications 19850 }
        

sdsEventResourceUserDeRegisteredNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Resource-User Deregistered"
    ::= { sdsMIBNotifications 19851 }
        

sdsEventResourceRoutingStateNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Resource Routing State Changed"
    ::= { sdsMIBNotifications 19852 }
        

sdsEventHaEgressMessageDiscardedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Resource Egress Message Discarded"
    ::= { sdsMIBNotifications 19853 }
        

sdsEventHaRPTTAuditResultNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Resource-Provider Tracking Table Audit Results"
    ::= { sdsMIBNotifications 19854 }
        

sdsComAgentMaxConnsInConnGrpNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Max connections per connection group limit is reached."
    ::= { sdsMIBNotifications 19863 }
        

sdsEventSvcProvRegStateChangedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Service Provider Registration State Changed"
    ::= { sdsMIBNotifications 19856 }
        

sdsEventSvcProvOpStateChangedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Service Provider Operational State Changed"
    ::= { sdsMIBNotifications 19857 }
        

sdsEventComAgentRejConnUnknownIpNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Connection Rejected"
    ::= { sdsMIBNotifications 19858 }
        

sdsConnectionDownNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Connection Down"
    ::= { sdsMIBNotifications 19800 }
        

sdsConnLocalBlockedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Connection Locally Blocked"
    ::= { sdsMIBNotifications 19801 }
        

sdsConnRemoteBlockedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Connection Remotely Blocked"
    ::= { sdsMIBNotifications 19802 }
        

sdsQueueUtilNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The percent utilization of the Communication Agent Task stack queue is approaching defined threshold capacity."
    ::= { sdsMIBNotifications 19803 }
        

sdsClientConnWaitNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent configured connection waiting for remote client to establish connection"
    ::= { sdsMIBNotifications 19804 }
        

sdsRSUnavailNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Routed Service Unavailable"
    ::= { sdsMIBNotifications 19820 }
        

sdsRSDegradedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Routed Service Degraded"
    ::= { sdsMIBNotifications 19821 }
        

sdsRSCongestedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Routed Service Congested"
    ::= { sdsMIBNotifications 19822 }
        

sdsRSUsingLowPriConnGrpNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent routed service is routing traffic using a connection group that has a lower-priority than another connection group."
    ::= { sdsMIBNotifications 19823 }
        

sdsTransUtilNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The ComAgent Reliable Transfer Function is approaching or exceeding its engineered reliable transaction handling capacity."
    ::= { sdsMIBNotifications 19824 }
        

sdsTransFailRateNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The number of failed transactions during the sampling period has exceeded configured thresholds."
    ::= { sdsMIBNotifications 19825 }
        

sdsConnCongestedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Connection Congested"
    ::= { sdsMIBNotifications 19826 }
        

sdsConnAlignFailedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Failed to Align Connection."
    ::= { sdsMIBNotifications 19805 }
        

sdsResourceCongestedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Resource Degraded"
    ::= { sdsMIBNotifications 19846 }
        

sdsResourceUnavailNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Resource Unavailable"
    ::= { sdsMIBNotifications 19847 }
        

sdsResourceErrorNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Resource Error"
    ::= { sdsMIBNotifications 19848 }
        

sdsPoolResUtilNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The percent utilization of the Communication Agent CommMessage mempool is approaching defined threshold capacity."
    ::= { sdsMIBNotifications 19806 }
        

sdsDataEvPoolResUtilNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The percent utilization of the Communication Agent DataEvent mempool is approaching defined threshold capacity."
    ::= { sdsMIBNotifications 19818 }
        

sdsUserDataFIFOUtilNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The percent utilization of the Communication Agent User Data FIFO Queue is approaching defined threshold capacity."
    ::= { sdsMIBNotifications 19807 }
        

sdsMxFIFOUtilNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The percent utilization of the Communication Agent Mx FIFO Queue is approaching defined threshold capacity."
    ::= { sdsMIBNotifications 19808 }
        

sdsMultipleActivesNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Resource Has Multiple Actives"
    ::= { sdsMIBNotifications 19855 }
        

sdsTableMonitorFailureNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "ComAgent Configuration Daemon Table Monitoring Failure"
    ::= { sdsMIBNotifications 19860 }
        

sdsScriptFailureNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "ComAgent Configuration Daemon Script Failure"
    ::= { sdsMIBNotifications 19861 }
        

sdsIngressRateNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The Communication Agent Ingress Stack Event Rate is approaching its defined threshold capacity."
    ::= { sdsMIBNotifications 19862 }
        

sdsEventSuccessSetHostServerHWProfileNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "ComAgent Successfully Set Host Server Hardware Profile"
    ::= { sdsMIBNotifications 19864 }
        

sdsEventFailToSetHostServerHWProfileNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "ComAgent Failed to Set Host Server Hardware Profile"
    ::= { sdsMIBNotifications 19865 }
        

sdsEventPeerGroupStatusChangeNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Peer Group Status Changed"
    ::= { sdsMIBNotifications 19866 }
        

sdsEventPSEgressMessageDiscardedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Peer Group Egress Message Discarded"
    ::= { sdsMIBNotifications 19867 }
        

sdsEventConnectionRejectNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Communication Agent Connection Rejected. Connection to peer node is not initiated due to network incompatibility"
    ::= { sdsMIBNotifications 19868 }
        

sdsSmsQueueUtilNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The percent utilization of the SMS Task stack queue is approaching defined threshold capacity."
    ::= { sdsMIBNotifications 19827 }
        

sdsBDFQFullNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The BDF work queue depth size has reached full capacity."
    ::= { sdsMIBNotifications 19420 }
        

sdsBDFThrotlNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The BDF subsystem is throttling traffic at sender."
    ::= { sdsMIBNotifications 19421 }
        

sdsBroadcastDataFrameworkInvalidStackEventNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The BDF subsystem received a StackEvent that was somehow invalid, corrupt, or could not be delivered to the application."
    ::= { sdsMIBNotifications 19422 }
        

sdsProvInterfaceDisabledNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Provisioning interface is manually disabled. All connection attempts are denied."
    ::= { sdsMIBNotifications 14100 }
        

sdsProvNoRemoteConnectionsNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "No remote provisioning clients are connected."
    ::= { sdsMIBNotifications 14101 }
        

sdsProvConnectionFailedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Provisioning client connection establishment failed."
    ::= { sdsMIBNotifications 14102 }
        

sdsProvBothPortsAreTheSameNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Provisioning ports are the same."
    ::= { sdsMIBNotifications 14103 }
        

sdsProvConnectionEstablishedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Provisioning client connection established."
    ::= { sdsMIBNotifications 14120 }
        

sdsProvConnectionTerminatedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Provisioning client connection terminated."
    ::= { sdsMIBNotifications 14121 }
        

sdsProvConnectionDeniedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Provisioning client connection denied."
    ::= { sdsMIBNotifications 14122 }
        

sdsProvImportThrottledNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Import operation is throttled."
    ::= { sdsMIBNotifications 14140 }
        

sdsProvImportInitializationFailedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Configuration error"
    ::= { sdsMIBNotifications 14150 }
        

sdsProvImportGenerationFailedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Failed to import file"
    ::= { sdsMIBNotifications 14151 }
        

sdsProvImportTransferFailedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Failed to transfer file from remote host"
    ::= { sdsMIBNotifications 14152 }
        

sdsProvExportInitializationFailedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Configuration error"
    ::= { sdsMIBNotifications 14153 }
        

sdsProvExportGenerationFailedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Scheduled export failed"
    ::= { sdsMIBNotifications 14154 }
        

sdsProvExportTransferFailedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Failed to transfer file to remote host"
    ::= { sdsMIBNotifications 14155 }
        

sdsProvImportOperationCompletedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "All files were imported successfully"
    ::= { sdsMIBNotifications 14160 }
        

sdsProvExportOperationCompletedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "All scheduled exports completed successfully"
    ::= { sdsMIBNotifications 14161 }
        

sdsProvRemoteAuditStartedAndInProgressNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Remote Audit started and is in progress"
    ::= { sdsMIBNotifications 14170 }
        

sdsProvRemoteAuditAbortedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Remote Audit aborted"
    ::= { sdsMIBNotifications 14171 }
        

sdsProvRemoteAuditFailedToCompleteNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Remote Audit failed to complete"
    ::= { sdsMIBNotifications 14172 }
        

sdsProvRemoteAuditCompletedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Remote Audit completed"
    ::= { sdsMIBNotifications 14173 }
        

sdsProvNpaSplitPendingRequestDeletedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "NPA Split pending request deleted"
    ::= { sdsMIBNotifications 14174 }
        

sdsProvNpaSplitActivationFailedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "NPA Split activation failed"
    ::= { sdsMIBNotifications 14175 }
        

sdsProvNpaSplitStartedAndIsActiveNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "NPA Split started and is active"
    ::= { sdsMIBNotifications 14176 }
        

sdsProvNpaSplitCompletionFailedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "NPA Split completion failed"
    ::= { sdsMIBNotifications 14177 }
        

sdsProvNpaSplitCompletedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "NPA Split Completed"
    ::= { sdsMIBNotifications 14178 }
        

sdsProvMsisdnDeletedFromBlacklistNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Previously Blacklisted MSISDN is now a Routing Entity"
    ::= { sdsMIBNotifications 14179 }
        

sdsProvImsiDeletedFromBlacklistNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Previously Blacklisted IMSI is now a Routing Entity"
    ::= { sdsMIBNotifications 14180 }
        

sdsProvRelayNotConnectedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The PDB Relay feature is enabled but the connection to the HLRR is not established"
    ::= { sdsMIBNotifications 14188 }
        

sdsProvRelayTimeLagNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The time lag in seconds is getting too large between timestamps of last record PdbRelay processed and latest entry in the Command Log."
    ::= { sdsMIBNotifications 14189 }
        

sdsProvDbExceptionNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "A database operation has failed in an unexpected way. The severity increases as the number of failures per second increases."
    ::= { sdsMIBNotifications 14198 }
        

sdsDpsStackEventQueueUtilizationNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "The percent utilization of the DP Stack Event Queue is approaching its maximum capacity."
    ::= { sdsMIBNotifications 14200 }
        

sdsDpsDrmpStateMismatchNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "DRMP status has changed since DP process initialization. Application restart is required."
    ::= { sdsMIBNotifications 14201 }
        

sdsEraResponderFailedNotify NOTIFICATION-TYPE
    OBJECTS { sdsAlarmSrcNode, sdsAlarmNumber, sdsAlarmInstance,
              sdsAlarmSeverity, sdsAlarmText, sdsAlarmInfo,
              sdsAlarmGroup, sdsServerHostname,
              sdsAlarmSequence, sdsAlarmTimestamp,
              sdsAlarmEventType, sdsAlarmProbableCause,
              sdsAlarmAdditionalInfo }
    STATUS  current
    DESCRIPTION
            "Event Responder Failed"
    ::= { sdsMIBNotifications 14301 }
        


END
